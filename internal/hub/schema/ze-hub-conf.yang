module ze-hub-conf {
    namespace "urn:ze:hub:conf";
    prefix hub;

    import ze-extensions { prefix ze; }

    description "Hub/core configuration for ZeBGP";

    revision 2026-01-01 {
        description "Initial revision";
    }

    // Environment block - ZeBGP-specific settings
    container environment {
        description "ZeBGP environment settings";

        container daemon {
            description "Daemon settings";
            leaf pid { type string; }
            leaf user { type string; }
            leaf daemonize { type boolean; }
            leaf drop { type boolean; }
            leaf umask { type string; }
        }

        container log {
            description "Logging settings";

            // Base log level for all subsystems (ze.log)
            leaf level {
                type string;
                description "Base log level for all subsystems: disabled, debug, info, warn, err";
            }

            // Log output backend
            leaf backend {
                type string;
                description "Log output destination: stderr (default), stdout, syslog";
            }

            // Syslog destination address
            leaf destination {
                type string;
                description "Syslog address when backend=syslog";
            }

            // Plugin stderr relay level
            leaf relay {
                type string;
                description "Plugin stderr relay level: disabled, debug, info, warn, err";
            }

            // Legacy ExaBGP-compatible settings (deprecated)
            leaf enable { type boolean; }
            leaf all { type boolean; }
            leaf configuration { type boolean; }
            leaf reactor { type boolean; }
            leaf daemon { type boolean; }
            leaf processes { type boolean; }
            leaf network { type boolean; }
            leaf statistics { type boolean; }
            leaf packets { type boolean; }
            leaf rib { type boolean; }
            leaf message { type boolean; }
            leaf timers { type boolean; }
            leaf routes { type boolean; }
            leaf parser { type boolean; }
            leaf short { type boolean; }

            // Subsystem-specific log levels (any key allowed)
            // Syntax: <subsystem-path> <level>;
            // Example: bgp.routes debug;
            // Maps to: ze.log.bgp.routes=debug
            ze:allow-unknown-fields;
        }

        container tcp {
            description "TCP settings";
            leaf port { type uint16; }
            leaf attempts { type int32; }
            leaf delay { type int32; }
            leaf acl { type boolean; }
        }

        container bgp {
            description "BGP protocol settings";
            leaf connection { type string; description "Connection mode: both, passive, active"; }
            leaf openwait { type int32; }
        }

        container cache {
            description "Cache settings";
            leaf attributes { type boolean; }
        }

        container api {
            description "API settings";
            leaf ack { type boolean; }
            leaf chunk { type int32; }
            leaf encoder { type string; }
            leaf compact { type boolean; }
            leaf respawn { type boolean; }
            leaf terminate { type boolean; }
            leaf cli { type boolean; }
            leaf pipename { type string; }
            leaf socketname { type string; }
        }

        container reactor {
            description "Reactor settings";
            leaf speed { type string; }
            leaf cache-ttl { type uint32; description "Update cache TTL in seconds (0=immediate, default 60)"; }
            leaf cache-max { type uint32; description "Update cache max entries (0=unlimited, default 1000000)"; }
        }

        container debug {
            description "Debug settings";
            leaf pdb { type boolean; }
            leaf memory { type boolean; }
            leaf configuration { type boolean; }
            leaf selfcheck { type boolean; }
            leaf route { type string; }
            leaf defensive { type boolean; }
            leaf rotate { type boolean; }
            leaf timing { type boolean; }
            leaf pprof { type string; description "pprof HTTP server address (e.g. :6060)"; }
        }
    }
}
