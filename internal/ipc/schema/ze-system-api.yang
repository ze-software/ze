module ze-system-api {
    namespace "urn:ze:system:api";
    prefix sys;

    import ze-types { prefix zt; }

    description
        "System-level API operations for Ze.
         RPCs for version queries, shutdown, and command introspection.";

    revision 2026-02-01 {
        description "Initial revision";
    }

    rpc help {
        description "Show available commands";
        output {
            leaf-list subcommands { type string; description "Available subcommands"; }
        }
    }

    rpc version-software {
        description "Show ze version";
        output {
            leaf version { type string; description "Software version string"; }
        }
    }

    rpc version-api {
        description "Show IPC protocol version";
        output {
            leaf version { type string; description "API protocol version"; }
        }
    }

    // Daemon lifecycle (system-wide operations affecting all plugins)

    rpc daemon-shutdown {
        description "Gracefully shutdown the daemon";
    }

    rpc daemon-status {
        description "Query daemon status";
        output {
            leaf uptime-seconds { type uint32; description "Seconds since start"; }
            leaf peer-count { type uint32; description "Number of configured peers"; }
            leaf start-time { type string; description "ISO 8601 start timestamp"; }
        }
    }

    rpc daemon-reload {
        description "Reload configuration";
    }

    rpc subsystem-list {
        description "List available subsystems";
        output {
            list subsystem {
                leaf name { type string; description "Subsystem name"; }
                leaf description { type string; description "Subsystem description"; }
            }
        }
    }

    rpc command-list {
        description "List all available commands";
        output {
            list command {
                uses zt:command-info;
            }
        }
    }

    rpc command-help {
        description "Get detailed help for a command";
        input {
            leaf name { type string; mandatory true; description "Command name"; }
        }
        output {
            leaf help { type string; description "Detailed help text"; }
        }
    }

    rpc command-complete {
        description "Tab completion for partial commands";
        input {
            leaf partial { type string; mandatory true; description "Partial command string"; }
            leaf arg { type string; description "Current argument being completed"; }
        }
        output {
            leaf-list completions { type string; description "Completion candidates"; }
        }
    }

    rpc dispatch {
        description "Dispatch a text command through the command dispatcher";
        input {
            leaf-list args { type string; description "Command words to join and dispatch"; }
        }
        output {
            leaf status { type string; description "Result status (ok or error)"; }
            leaf data { type string; description "Response data"; }
        }
    }
}
