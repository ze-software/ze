module exabgp {
    namespace "urn:exabgp:config";
    prefix exabgp;

    import ze-types { prefix zt; }
    import ze-extensions { prefix ze; }

    description "ExaBGP configuration syntax for migration to ZeBGP.";

    revision 2026-01-01 {
        description "ExaBGP syntax for migration";
    }

    // Route attributes grouping (used in announce/static blocks)
    grouping route-attributes {
        leaf next-hop { type string; }
        leaf origin { type string; }
        leaf local-preference { type uint32; }
        leaf med { type uint32; }
        leaf as-path { ze:syntax "value-or-array"; ze:ordered; type string; }
        leaf community { ze:syntax "value-or-array"; type string; }
        leaf extended-community { ze:syntax "value-or-array"; type string; }
        leaf large-community { ze:syntax "value-or-array"; type string; }
        leaf aggregator { type string; }
        container atomic-aggregate { ze:syntax "flex"; }
        leaf originator-id { type zt:ipv4-address; }
        leaf cluster-list { ze:syntax "value-or-array"; type string; }
        leaf rd { type string; }
        leaf label { type string; }
        leaf labels { ze:syntax "value-or-array"; ze:ordered; type string; }
        leaf path-information { type string; }
        leaf name { type string; }
        leaf watchdog { type string; }
        leaf split { type string; }
        leaf bgp-prefix-sid { ze:syntax "value-or-array"; type string; description "BGP Prefix-SID (RFC 8669)"; }
        container attribute { ze:syntax "flex"; }
        container bgp-prefix-sid-srv6 { ze:syntax "flex"; }
        container withdraw { ze:syntax "flex"; }
    }

    // Top-level process definitions
    list process {
        key "name";
        leaf name { type string; }
        leaf run { ze:syntax "multi-leaf"; type string; }
        leaf encoder { type string; }
        leaf respawn { type boolean; }
        leaf on-exit { type string; }
    }

    // ExaBGP uses 'neighbor' not 'peer'
    list neighbor {
        key "address";
        leaf address { type string; }
        uses neighbor-fields;
    }

    // Template definitions
    container template {
        list neighbor {
            key "name";
            leaf name { type string; }
            uses neighbor-fields;
        }
    }

    grouping neighbor-fields {
        leaf description { type string; }
        leaf router-id { type zt:ipv4-address; }
        leaf local-address { type string; }
        leaf local-as { type zt:asn; }
        leaf peer-as { type zt:asn; }
        // ExaBGP's default in 4.2, 5.0 and 6.0 (migrate_defaults.go, exabgpHoldTimeDefault).
        leaf hold-time { type uint16; default 180; }
        leaf passive { type boolean; default false; }
        leaf group-updates { type boolean; default true; }
        // Accepted and dropped: ExaBGP has not read it since 4.0.4 (migrate.go,
        // copySimpleFields).
        leaf auto-flush { type boolean; default true; }
        leaf manual-eor { type boolean; default false; }
        // ExaBGP peer.py: `Notify(6, 2) if neighbor.shutdown`, the peer starts disabled.
        leaf shutdown { type boolean; default false; }
        // ExaBGP 6.0 receive policy (f9bfb853b, grammar/tree/neighbor.py):
        // as-set withdraw|accept, tunnel-encapsulation auto|filter|accept.
        // The enumerations are ExaBGP's own value sets, so a value ExaBGP
        // rejects is refused here; migrate_receive_policy.go then refuses
        // the values ze cannot reproduce.
        leaf as-set {
            type enumeration {
                enum withdraw;
                enum accept;
            }
        }
        leaf tunnel-encapsulation {
            type enumeration {
                enum auto;
                enum filter;
                enum accept;
            }
        }

        // Family block (ExaBGP uses space: "ipv4 unicast")
        container family {
            ze:syntax "freeform";
        }

        // Capabilities
        container capability {
            leaf asn4 { type boolean; default true; }
            container route-refresh { ze:syntax "flex"; }
            container graceful-restart {
                ze:syntax "flex";
                leaf restart-time { type uint16; default 120; }
            }
            container add-path {
                ze:syntax "flex";
                leaf send { type boolean; default false; }
                leaf receive { type boolean; default false; }
            }
            container extended-message { ze:syntax "flex"; }
            container nexthop { ze:syntax "flex"; }
            container multi-session { ze:syntax "flex"; }
            container operational { ze:syntax "flex"; }
            container aigp { ze:syntax "flex"; }
            container software-version { ze:syntax "flex"; }
            container link-local-nexthop { ze:syntax "flex"; }
        }

        // Additional fields
        leaf host-name { type string; }
        leaf domain-name { type string; }
        leaf inherit { type string; }
        leaf md5-password { type string; }
        leaf ttl-security { type uint16; }
        leaf local-link-local { type string; }

        // API block (ExaBGP-specific). ExaBGP takes an optional name after the
        // keyword and invents one when it is absent (auto-named-<microseconds>,
        // src/exabgp/configuration/neighbor/api.py ParseAPI.pre), so a neighbor
        // can carry several blocks. The name groups the settings for a reader
        // and changes no semantics: ParseAPI.flatten unions every block's
        // processes and per-direction flags into one set. A keyed list accepts
        // the anonymous form under config.KeyDefault and the named form under
        // its name, and the migration unions the entries the same way.
        list api {
            key "name";
            leaf name { type string; }
            leaf-list processes { ze:syntax "bracket"; type string; }
            leaf-list processes-match { ze:syntax "bracket"; type string; }
            // The four events that are not a BGP message. ExaBGP writes each as
            // a bare word in the api block, and grants it to that block's
            // processes (src/exabgp/configuration/neighbor/api.py, ParseAPI).
            container neighbor-changes { ze:syntax "flex"; }
            container negotiated { ze:syntax "flex"; }
            container fsm { ze:syntax "flex"; }
            container signal { ze:syntax "flex"; }
            container receive { ze:syntax "freeform"; }
            container send { ze:syntax "freeform"; }
        }

        // Process bindings
        list process {
            key "name";
            leaf name { type string; }
            leaf-list processes { ze:syntax "bracket"; type string; }
            container receive { ze:syntax "freeform"; }
            container send { ze:syntax "freeform"; }
        }

        // Static routes
        container static {
            container route {
                ze:syntax "inline-list";
                ze:key-type "prefix";
                uses route-attributes;
            }
        }

        // Announce block - structured by AFI/SAFI
        container announce {
            container ipv4 {
                container unicast {
                    ze:syntax "inline-list";
                    ze:key-type "prefix";
                    uses route-attributes;
                }
                container multicast {
                    ze:syntax "inline-list";
                    ze:key-type "prefix";
                    uses route-attributes;
                }
                container nlri-mpls {
                    ze:syntax "inline-list";
                    ze:key-type "prefix";
                    uses route-attributes;
                }
                container mpls-vpn {
                    ze:syntax "inline-list";
                    ze:key-type "prefix";
                    uses route-attributes;
                }
                container mcast-vpn { ze:syntax "flex"; }
                container mup { ze:syntax "flex"; }
                container flow { ze:syntax "flex"; }
                container sr-policy { ze:syntax "flex"; }
            }
            container ipv6 {
                container unicast {
                    ze:syntax "inline-list";
                    ze:key-type "prefix";
                    uses route-attributes;
                }
                container multicast {
                    ze:syntax "inline-list";
                    ze:key-type "prefix";
                    uses route-attributes;
                }
                container nlri-mpls {
                    ze:syntax "inline-list";
                    ze:key-type "prefix";
                    uses route-attributes;
                }
                container mpls-vpn {
                    ze:syntax "inline-list";
                    ze:key-type "prefix";
                    uses route-attributes;
                }
                container mcast-vpn { ze:syntax "flex"; }
                container mup { ze:syntax "flex"; }
                container flow { ze:syntax "flex"; }
                container sr-policy { ze:syntax "flex"; }
            }
            container l2vpn {
                container vpls { ze:syntax "flex"; }
                container evpn { ze:syntax "flex"; }
            }
            container route {
                ze:syntax "inline-list";
                ze:key-type "prefix";
                uses route-attributes;
            }
        }

        // L2VPN (structured to support inline + named blocks)
        container l2vpn {
            container vpls {
                ze:syntax "flex";
                uses route-attributes;
                leaf endpoint { type uint16; }
                leaf ve-id { type uint16; }
                leaf base { type uint32; }
                leaf offset { type uint16; }
                leaf ve-block-offset { type uint16; }
                leaf size { type uint16; }
                leaf ve-block-size { type uint16; }
            }
        }

        // Flow (FlowSpec routes)
        container flow {
            list route {
                key "name";
                leaf name { type string; }
                leaf rd { type string; }
                leaf next-hop { type string; }
                container match { ze:syntax "freeform"; }
                container then { ze:syntax "freeform"; }
                // The third section of an ExaBGP flow route, beside match and
                // then. It carries interface-set extended communities
                // (src/exabgp/configuration/flow/scope.py ParseFlowScope).
                container scope { ze:syntax "freeform"; }
            }
        }

        // Nexthop encoding (RFC 8950)
        container nexthop { ze:syntax "freeform"; }

        // Add-path per family
        container add-path { ze:syntax "freeform"; }
    }
}
