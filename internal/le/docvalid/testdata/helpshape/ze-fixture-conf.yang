// A config module for the help shape gate's tests. It is read as a file rather
// than as a Go string so the gate's owner resolution runs over real YANG text,
// braces and all.
//
// The module, the revision and the grouping each carry a paragraph no one-line
// row renders. They are here to prove the caps do NOT reach them: three agents
// given a brief with no population rule shortened exactly these statements and
// moved the prose into comments, which is a downgrade.
//
// The choice and the case carry a paragraph each for the same reason. Neither
// is emitted as a completion row: effectiveChildren walks through both.
//
// Two enumerations sit in it on purpose. The one on `family` keys a list and
// the one on `state` keys nothing: the completer renders each value's ze:help
// on a one-line row either way, so both take the caps. The typedef one is
// used by no leaf, so no row renders it and no bound reaches it.
module ze-fixture-conf {
  namespace "urn:ze:fixture:conf";
  prefix zefixconf;
  import ze-extensions { prefix ze; }

  description
    "The module statement describes the whole schema for a reader who opens the
     file, so it is written as a paragraph and it runs well past ninety-six
     characters and well past twenty-five words. No completion row renders it,
     and no gate caps it.";

  revision 2026-09-03 {
    description
      "The revision statement records what changed in this version of the schema,
       so it is written as a paragraph too, and it also runs well past ninety-six
       characters and well past twenty-five words. No completion row renders it
       either.";
  }

  grouping socket-common {
    description
      "A grouping is a reusable block that no completion row names, so its own
       description is written as a paragraph and runs past both bounds without a
       gate saying anything about it.";

    leaf backlog {
      type uint16;
      description "The kernel queues connections on this listener until the daemon accepts them.";
      ze:help "Pending connections the listener holds.";
    }
  }

  typedef socket-state {
    type enumeration {
      enum listening {
        ze:help
          "An enumeration reached through a typedef carries no help to any row,
           because the completer reads an enum's ze:help off the leaf's own
           node, so this paragraph past both bounds is never rendered.";
      }
    }
    description "The state a socket is in.";
  }

  container sockets {
    description "The container groups every socket the daemon opens on behalf of a peer.";
    ze:help "Socket state the operator can set.";

    uses socket-common;

    leaf state {
      type enumeration {
        enum open {
          ze:help "The socket accepts connections.";
        }
      }
      description "The state is read from the kernel each time the row is drawn.";
      ze:help "Whether the socket is open.";
    }

    choice delivery {
      ze:help
        "A choice statement is schema structure that effectiveChildren walks
         through. Its own ze:help reaches no completion row. This paragraph
         runs past both bounds and is rendered nowhere.";

      case immediate {
        ze:help
          "A case statement is walked through in the same way. This paragraph
           runs past both bounds. No bound of this gate reaches it.";

        leaf deadline {
          type uint16;
          description "The timer starts when the socket enters the closing state.";
          ze:help "Seconds the daemon waits before it drops the socket.";
        }
      }
    }

    list binding {
      key "family";
      description "A binding names the family the listener opens a socket for.";
      ze:help "One binding for each address family.";

      leaf family {
        type enumeration {
          enum ipv4 {
            ze:help "Bind the listener to IPv4 only.";
          }
          enum ipv6 {
            ze:help "Bind the listener to IPv6 only.";
          }
        }
        description "The listener binds one family, and a second listener carries the other.";
        ze:help "Address family the listener binds.";
      }

      leaf port {
        type uint16;
        description "The port is the local TCP port the listener accepts connections on.";
        ze:help "Port the listener binds.";
      }
    }
  }
}
