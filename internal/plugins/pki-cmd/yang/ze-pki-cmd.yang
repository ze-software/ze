module ze-pki-cmd {
    namespace "urn:ze:pki:cmd";
    prefix pkicmd;
    import ze-extensions    { prefix ze; }
    import ze-cli-show-cmd  { prefix clishowcmd; }
    description "PKI show commands: certificate listing and detailed inspection.
         Relocated from the central show schema for plugin self-containment.";
    revision 2026-09-03 { description "show pki local-ca pem exports the root of the certificate authority this daemon issues its own components' certificates from. It is a separate noun from certificate, which addresses an operator-configured store entry by name, because the local root is generated at first start and is named by nothing."; }
    revision 2026-08-30 { description "Each output form of show pki certificate name is its own command: pem, bundle pem and fingerprint. The forms are mutually exclusive tails, so the model states them as sibling containers rather than a description stating an alternation a handler switch reads."; }
    revision 2026-06-03 { description "Initial revision: relocated from ze-cli-show-cmd."; }

    augment "/clishowcmd:show" {
        container pki {
            config false;
            description "These are the certificates Ze itself presents and trusts for its own listeners
                         and clients. They are not the certificates a peer presents over BGP or IPsec.";
            ze:help "TLS certificates and CA trust store.";
            container certificates {
                config false;
                ze:command "ze-pki:show-certificates";
                ze:rpc "ze-pki-api:certificates";
                description "Shows name, type (CA or device), subject, issuer, expiry, and validity status.
Check here to find certificates approaching expiration.";
                ze:help "List all loaded certificates with expiry dates.";
            }
            container local-ca {
                config false;
                description "Ze generates this root at its first start and keeps it. It signs the leaf the plugin
                             hub and the management hub serve. It is not one of the certificates the pki block
                             configures, and it has no name.";
                ze:help "The certificate authority this daemon issues its own components' certificates from.";
                container pem {
                    config false;
                    ze:command "ze-pki:show-local-ca-pem";
                    description "Give this text to each client that must trust this node, in its
                                 `pki ca <name> certificate` block. The output holds the certificate only:
                                 the root private key never leaves the daemon.";
                    ze:help "Export the root certificate of the local certificate authority as PEM.";
                }
            }

            container certificate {
                config false;
                description "The detail view decodes the certificate for a reader. An export form writes it in
                             a shape another program consumes, and the two answer the same certificate.";
                ze:help "Inspect a specific certificate in detail or export forms.";
                container name {
                    config false;
                    ze:command "ze-pki:show-certificate";
                    ze:rpc "ze-pki-api:certificate";
                    description "Each export form is a command of its own.";
                    ze:help "Inspect a specific certificate in detail.";
                    leaf name {
                        type string;
                        mandatory true;
                        description "The name of a CA or device certificate in the store. An unknown
                                     name is refused, and the refusal lists the names the store holds.";
                        ze:help "Certificate name";
                    }

                    container pem {
                        config false;
                        ze:command "ze-pki:show-certificate-pem";
                        description "Use this form to give the certificate to another system.";
                        ze:help "Export the certificate, and any intermediate it carries, as PEM.";
                        leaf name {
                            type string;
                            mandatory true;
                            description "The name of a CA or device certificate in the store. An
                                         unknown name is refused, and the refusal lists the names the
                                         store holds.";
                            ze:help "Certificate name";
                        }
                    }

                    container bundle {
                        config false;
                        description "A bundle carries the chain, so it holds the issuers a verifier needs and not the
                                     leaf alone. Use the plain PEM export when only the certificate is wanted.";
                        ze:help "Export forms that carry more than the certificate.";

                        container pem {
                            config false;
                            ze:command "ze-pki:show-certificate-bundle-pem";
                            description "Device certificates only: a CA certificate in the store holds no private key.";
                            ze:help "Export the certificate, its intermediates and its private key as one PEM stream.";
                            leaf name {
                                type string;
                                mandatory true;
                                description "The name of a device certificate in the store. A CA name
                                             and a device certificate with no private key are each
                                             refused.";
                                ze:help "Certificate name";
                            }
                        }
                    }

                    container fingerprint {
                        config false;
                        ze:command "ze-pki:show-certificate-fingerprint";
                        description "Without an algorithm, SHA-256.";
                        ze:help "Show the hash of the certificate, to verify its identity against the one another system reports.";
                        leaf name {
                            type string;
                            mandatory true;
                            description "The name of a CA or device certificate in the store. The hash
                                         is taken over its DER bytes. An unknown name is refused, and
                                         the refusal lists the names the store holds.";
                            ze:help "Certificate name";
                        }

                        container algorithm {
                            config false;
                            ze:modifier "choice";
                            description "The keyword takes one word, sha256, sha384 or sha512, and the
word is case-insensitive. Any other word fails with the message 'pki:
unsupported hash algorithm'. A second word after the algorithm is refused.";
                            ze:help "Which hash to take of the certificate.";
                            leaf algorithm {
                                type enumeration {
                                    enum sha256 { ze:help "Hash the certificate with SHA-256, a 32-byte digest."; }
                                    enum sha384 { ze:help "Hash the certificate with SHA-384, a 48-byte digest."; }
                                    enum sha512 { ze:help "Hash the certificate with SHA-512, a 64-byte digest."; }
                                }
                                description "The digest is printed as hex bytes separated by colons, beside
                                             the algorithm name. The word is lowered before it is matched,
                                             and a word outside the three is refused.";
                                ze:help "Hash algorithm. Without one, sha256.";
                            }
                        }
                    }
                }
            }
        }
    }
}
