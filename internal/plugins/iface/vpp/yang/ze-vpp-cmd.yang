module ze-vpp-cmd {
    namespace "urn:ze:vpp:cmd";
    prefix vppcmd;
    import ze-extensions { prefix ze; }
    description "show vpp ... command tree. Owned by the VPP backend plugin so that removing the VPP surface removes these command nodes together with the handlers. See ai/rules/plugin-self-containment.md.";
    revision 2026-06-03 { description "Relocated show vpp ... out of the central show schema (plugin self-containment)."; }

    container show {
        config false;
        ze:help "Read-only commands to inspect system, protocol, and network state.";

        container vpp {
            config false;
            ze:backend "vpp";
            description "These read the VPP dataplane rather than the kernel, so a router forwarding in the
                         kernel has nothing to report here.";
            ze:help "VPP dataplane tracing and runtime statistics.";

            container trace {
                config false;
                description "A trace is armed, filled by traffic, and then read. It costs the dataplane while
                             it is armed, so it is a diagnostic tool rather than something to leave running.";
                ze:help "Capture and inspect VPP dataplane packet traces.";

                container start {
                    config false;
                    ze:command "ze-iface:show-vpp-trace-start";
                    description "Default input node is dpdk-input, default count is 100 (max 10000). After
starting, use 'show vpp trace show' to retrieve the captured packets. Requires
the VPP backend.";
                    ze:help "Start capturing packets in the VPP dataplane.";
                }

                container show {
                    config false;
                    ze:command "ze-iface:show-vpp-trace-show";
                    description "Shows per-packet VPP graph node traversal. Requires the VPP backend.";
                    ze:help "Retrieve packets captured since the last trace start.";
                }

                container clear {
                    config false;
                    ze:command "ze-iface:show-vpp-trace-clear";
                    description "Clears all packets so you can start a fresh trace. Requires the VPP backend.";
                    ze:help "Discard the captured VPP trace buffer.";
                }
            }

            container runtime {
                config false;
                ze:command "ze-iface:show-vpp-runtime";
                description "Returns per-node packet counts, vectors, clocks, and suspends. Helps you find
which node is the bottleneck. Requires the VPP backend.";
                ze:help "Show VPP graph node processing statistics.";
            }
        }
    }
}
