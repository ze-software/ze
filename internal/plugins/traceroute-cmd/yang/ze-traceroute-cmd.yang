module ze-traceroute-cmd {
    namespace "urn:ze:traceroute:cmd";
    prefix traceroutecmd;
    import ze-extensions { prefix ze; }
    description "traceroute command tree (show traceroute, show probe-round, monitor traceroute, resolve traceroute). Owned by the dedicated traceroute feature module so that the whole traceroute surface lives in one place and container-merges onto the show, monitor, and resolve verb roots. See ai/rules/plugin-self-containment.md.";
    revision 2026-09-15 { description "Add the do-not-fragment keyword to show traceroute and resolve traceroute. The probe layer gained a Don't Fragment mode, and the keyword is the same word on ping."; }
    revision 2026-09-05 { description "Say that the source of resolve traceroute selects the address family the target is resolved in. The handler now reads the source before it resolves the target."; }
    revision 2026-08-29 { description "Declare the target and the four optional values of resolve traceroute. The handler already reads them as keyword pairs; the description spelled them in prose and the model stated nothing."; }
    revision 2026-06-03 { description "Relocate the traceroute command surface out of the central show, monitor, and resolve schemas into the dedicated traceroute module."; }

    container show {
        config false;
        ze:help "Read-only commands to inspect system, protocol, and network state.";

        container traceroute {
            config false;
            ze:command "ze-show:traceroute";
            description "Shows each hop with its IP and round-trip time. Dest can be an IP or hostname.
Defaults: 30 max hops, 3 probes per hop. Increase probes for more reliable RTT
measurements.";
            ze:help "Trace the network path from this router to a target.";
            leaf dest {
                type string;
                description "The value is the first bare word of the command. A host name is resolved
in either address family, and the family of the answer selects ICMPv4 or ICMPv6.";
                ze:help "Target host or IP address.";
            }
            leaf max-hops {
                type uint32;
                description "The value is the largest time-to-live Ze probes, 1 to 64. The trace stops
early when the target answers. Absent, the value is 30.";
                ze:help "Maximum number of hops.";
            }
            leaf timeout {
                type string {
                    pattern '\d+[smh]?';
                }
                description "The value is the time Ze waits for one probe, in Go duration syntax, 1s
to 30s. Absent, the value is 3s.";
                ze:help "Timeout duration.";
            }
            leaf probes {
                type uint32;
                description "The value is the number of probes Ze sends at each time-to-live, 1 to 10,
and each probe reports its own round-trip time. Absent, the value is 3.";
                ze:help "Number of probes per hop.";
            }
            leaf do-not-fragment {
                type enumeration {
                    enum honor-cache { ze:help "Set the DF bit and refuse a probe larger than the kernel's cached path MTU."; }
                    enum bypass-cache { ze:help "Set the DF bit and ignore the cached path MTU, so the wire answers for itself."; }
                }
                description "The keyword takes one of two values. honor-cache sets the Don't Fragment bit
and honors the kernel's cached path MTU: a probe larger than the cached value is refused at
send time, and a router's Fragmentation Needed answer updates the cache. bypass-cache sets
the bit and ignores the cached value, so the probe is put on the wire at its full size.
Absent, the kernel fragments a probe larger than the path, which is the behavior of before
the keyword existed.";
                ze:help "Set the Don't Fragment bit; honor-cache obeys the cached path MTU, bypass-cache ignores it.";
            }
        }

        container probe-round {
            config false;
            ze:command "ze-show:probe-round";
            description "Sends all probes concurrently for faster results than sequential traceroute.
Returns per-hop RTT and IP. Use probes and max-hops to tune accuracy vs speed.";
            ze:help "Run a parallel traceroute probe round to a target.";
            leaf dest {
                type string;
                description "The value is the first bare word of the command. A host name is resolved
in either address family, and the family of the answer selects ICMPv4 or ICMPv6.";
                ze:help "Target host or IP address.";
            }
            leaf probes {
                type uint32;
                description "The value is accepted in the range 1 to 10 and then not read: a probe
round sends one probe at each time-to-live.";
                ze:help "Number of probes per hop.";
            }
            leaf max-hops {
                type uint32;
                description "The value is the largest time-to-live Ze probes, 1 to 64. Absent, or set
to 30, the round probes 16 hops.";
                ze:help "Maximum number of hops.";
            }
            leaf timeout {
                type string {
                    pattern '\d+[smh]?';
                }
                description "The value is accepted in Go duration syntax, 1s to 30s, and then not read:
a probe round waits one second for every answer.";
                ze:help "Timeout duration.";
            }
        }
    }

    container monitor {
        config false;
        ze:help "Continuous monitoring commands (Ctrl-C to stop).";

        container traceroute {
            config false;
            ze:command "ze-monitor:traceroute";
            ze:task-support required;
            description "Shows each hop with running RTT statistics. Keeps probing so you can watch
path changes and latency shifts over time.";
            ze:help "Live mtr-style traceroute that updates continuously.";
        }
    }

    container resolve {
        config false;
        ze:help "DNS, ASN, PeeringDB, and IRR resolution tools.";

        container traceroute {
            config false;
            ze:command "ze-resolve:traceroute";
            description "The options are source, max-hops, timeout and probes, each one a
keyword and a value, and do-not-fragment, a keyword with one of two values. max-hops is 1 to 64 and defaults to 30, probes is 1 to 10 and defaults
to 3, and timeout is 1s to 30s and defaults to 3s. The source also selects the address
family: a target name is resolved in the family of the source, and a target with no
address in that family is refused.";
            ze:help "Traceroute from the router with optional source binding.";
            leaf target {
                type string { pattern '[a-zA-Z0-9.:%-]+'; length "1..253"; }
                mandatory true;
                description "The value follows the target keyword. A host name is resolved in the family
of the source, or in either family when no source is given, and a name with no address in
that family is refused.";
                ze:help "Host or IP address to trace to.";
            }
            leaf source {
                type string { pattern '[0-9a-fA-F:.]+(%[a-zA-Z0-9_.-]+)?'; }
                description "The value is a local IPv4 or IPv6 address, with an optional %zone, that Ze
binds the probe socket to. Absent, the kernel picks the source.";
                ze:help "Source IP address to bind, whose family also selects the family the target is resolved in.";
            }
            leaf max-hops {
                type uint32 { range "1..64"; }
                description "The trace stops early when the target answers. Absent, the value is 30.";
                ze:help "Largest time-to-live to probe.";
            }
            leaf timeout {
                type string { pattern '([0-9]+(\.[0-9]+)?(ns|us|ms|s|m|h))+'; }
                description "The value is the time Ze waits for one probe before it records a missing
answer. Absent, the value is 3s.";
                ze:help "Per-probe timeout, 1s to 30s, in Go duration syntax.";
            }
            leaf probes {
                type uint32 { range "1..10"; }
                description "Each probe at one time-to-live reports its own round-trip time. Absent,
the value is 3.";
                ze:help "Number of probes per hop.";
            }
            leaf do-not-fragment {
                type enumeration {
                    enum honor-cache { ze:help "Set the DF bit and refuse a probe larger than the kernel's cached path MTU."; }
                    enum bypass-cache { ze:help "Set the DF bit and ignore the cached path MTU, so the wire answers for itself."; }
                }
                description "The keyword takes one of two values. honor-cache sets the Don't Fragment bit
and honors the kernel's cached path MTU: a probe larger than the cached value is refused at
send time, and a router's Fragmentation Needed answer updates the cache. bypass-cache sets
the bit and ignores the cached value, so the probe is put on the wire at its full size.
Absent, the kernel fragments a probe larger than the path, which is the behavior of before
the keyword existed.";
                ze:help "Set the Don't Fragment bit; honor-cache obeys the cached path MTU, bypass-cache ignores it.";
            }
        }
    }
}
