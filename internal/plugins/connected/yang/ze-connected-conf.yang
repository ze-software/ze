module ze-connected-conf {
    namespace "urn:ze:connected:conf";
    prefix connected;

    import ze-extensions { prefix ze; }
    import ze-policy-conf { prefix policy; }

    description
        "Connected route redistribution for Ze.
         When present, directly connected interface prefixes are
         advertised into BGP via the redistribute event bus.";

    revision 2026-05-12 {
        description "Initial revision.";
    }

    container connected {
        uses policy:rib-import-filter;
        description "The container carries no leaf, so writing it is the whole configuration.
                     The plugin watches each interface address event and emits the network
                     prefix of that address on the redistribute event bus. It counts the
                     addresses of one prefix, so two addresses in one subnet announce the prefix
                     once. The withdrawal waits for the last address of that prefix. The plugin
                     registers the connected route source, and a redistribute statement names
                     that source.";
        ze:help "Connected route redistribution. Presence enables the plugin.";
    }
}
