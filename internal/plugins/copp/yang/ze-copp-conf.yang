module ze-copp-conf {
    namespace "urn:ze:copp:conf";
    prefix copp;

    import ze-extensions { prefix ze; }

    description
        "Control-plane policing configuration for Ze.
         Protects host-bound traffic to the BGP listen port
         (TCP/179): an access list admits configured BGP neighbors
         and trusted sources and drops every other source, and an
         optional rate limits new connections from the neighbors.";

    revision 2026-10-27 {
        description "Access list built from the BGP neighbors; rate optional; over-limit-policy defaults to drop.";
    }

    revision 2026-06-26 {
        description "Initial revision.";
    }

    typedef rate-spec {
        type string {
            pattern '[0-9]+(bytes|kbytes|mbytes|gbytes)?/(second|minute|hour|day)';
        }
        description "Rate limit: packet-per-unit (10/second) or byte-per-unit (1mbytes/second).";
    }

    container control-plane-protection {
        description "Ze compiles the containers under it into one nftables table named ze_copp,
                     which carries a base input chain at priority 0. The ze_ prefix is what
                     makes the firewall backend own that table and withdraw it when you delete
                     the configuration. The bgp container is the only policy Ze builds today.";
        ze:help "Control-plane policing configuration.";

        container bgp {
            presence "BGP control-plane policing enabled";
            description "An access list on TCP to the protected ports (RFC 7454 Section 4). Ze
                         accepts an established or related connection first, then a connection
                         from each trusted-source prefix, then a connection from a configured
                         BGP neighbor: the remote ip of each static peer and the range of each
                         dynamic group, read from the bgp configuration. Ze counts and drops TCP
                         to a protected port from every other source. The rate, when set, limits
                         new connections from the neighbors only. Ze builds the table when you
                         write the container and removes it when you delete the container. A
                         configuration without this container gets no access list.";
            ze:help "Accept BGP connections from configured neighbors only, and drop the rest.";

            leaf rate {
                type rate-spec;
                description "The leaf is optional. Without it Ze builds the access list and no
                             limit. The value is a count, an optional byte unit, and a time unit,
                             as in 100/second or 1mbytes/second. The limit applies to new TCP
                             connections from configured BGP neighbors. A trusted-source prefix
                             and an established session never meet it, and a source that is not
                             a neighbor is dropped before it.";
                ze:help "Limit for new connections from BGP neighbors (e.g., 100/second).";
            }

            leaf burst {
                type uint32;
                description "The unit follows the unit of rate: a packet count where rate counts
                             packets, and a byte count where rate names a byte unit. The leaf
                             has no default, and Ze gives the kernel a burst of 0 when it is
                             absent. Ze refuses a burst without a rate.";
                ze:help "Burst size (packets or bytes matching the rate unit).";
            }

            leaf-list protected-port {
                type uint16 {
                    range "1..65535";
                }
                description "TCP port(s) to protect. Ze uses 179, the BGP port, when this leaf is omitted. Set a different value
                    when the BGP listener uses another port.";
                ze:help "TCP port(s) the control-plane policing rules protect, 179 (BGP) by default.";
            }

            leaf-list trusted-source {
                type string;
                ze:validate "ipv4-prefix|ipv6-prefix";
                description
                    "Ze adds one accept term for each prefix, ahead of the neighbor terms.
                     The term matches TCP from that source to a protected port, so a
                     trusted source is never dropped and never meets the rate limit. Use it
                     for a source that is not a configured BGP neighbor, such as a
                     monitoring host. Ze refuses a value that is not an IPv4 prefix or an
                     IPv6 prefix.";
                ze:help "Source prefixes accepted without being BGP neighbors, and never rate limited.";
            }

            leaf over-limit-policy {
                type enumeration {
                    enum accept {
                        ze:help "Accept over-limit connections; the limit then stops nothing.";
                    }
                    enum drop {
                        ze:help "Drop over-limit connections (default).";
                    }
                }
                default "drop";
                description "drop, the default, discards a new connection from a BGP neighbor once
                             the rate is exceeded. accept lets those connections through, so the
                             limit reports load and stops nothing; use it to observe a new rate
                             before you enforce it. The leaf matters only when rate is set, and it
                             never changes the access list: a source that is not a neighbor is
                             dropped under either setting. The input chain keeps an accept policy,
                             so SSH, ICMP and every service this table never names stay reachable,
                             and an established session is accepted before the limit is read.";
                ze:help "What Ze does with neighbor connections that exceed the rate limit.";
            }
        }
    }
}
