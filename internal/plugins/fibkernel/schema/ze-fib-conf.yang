module ze-fib-conf {
    namespace "urn:ze:fib:conf";
    prefix fib;

    description
        "FIB configuration for Ze.
         Contains the kernel backend configuration for route programming.
         Admin distance settings are in ze-sysrib-conf (RIB concept).";

    revision 2026-04-04 {
        description "Move admin-distance to ze-sysrib-conf.";
    }

    container fib {
        description "Forwarding Information Base configuration.";

        container kernel {
            description "OS kernel route programming via netlink (Linux).";

            leaf flush-on-stop {
                type boolean;
                default false;
                description
                    "Remove all ze-installed routes when the plugin stops.
                     When false (default), routes persist in the kernel
                     after shutdown for graceful restart support.";
            }

            leaf sweep-delay {
                type uint16;
                default 30;
                units seconds;
                description
                    "Time to wait after startup before sweeping stale routes.
                     Allows BGP reconvergence to refresh matching routes.";
            }
        }
    }
}
