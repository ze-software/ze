module ze-config-cli-cmd {
    namespace "urn:ze:config:cli:cmd";
    prefix configclicmd;
    import ze-extensions { prefix ze; }
    // These handlers inspect, compare, and format configuration files through
    // the config backend. See ai/rules/plugin-self-containment.md.
    description "The show config command tree, owned by the config CLI.";
    revision 2026-11-02 { description "Declare strip-private on show config dump, and check and diff on show config fmt, so every surface can make those choices."; }
    revision 2026-10-24 { description "Add show config running, the configuration the daemon applied, answered by the daemon."; }
    revision 2026-10-12 { description "Rename validate config to show config validation: the first word of a command is its verb."; }
    revision 2026-10-08 { description "Declare show config graph and validate config, which the config CLI already served."; }
    // Every command that enumerates a set now spells the verb the same way.
    revision 2026-08-31 { description "Renamed show config ls to show config list."; }
    // The model now states the grammar, and the generated usage line reads it.
    revision 2026-08-29 { description "Declare the value the description spelled in prose."; }
    revision 2026-06-06 { description "Relocated show config out of the central show schema (plugin self-containment)."; }

    container show {
        config false;
        ze:help "Read-only commands to inspect system, protocol, and network state.";

        container config {
            config false;
            description "Everything here reads. Nothing under show config applies a change, so it is safe
                         against a production router.";
            ze:help "Inspect, compare, and format configuration.";

            container dump {
                config false;
                ze:command "ze-config-cli:show-config-dump";
                description "Parses the config and outputs it after includes, defaults, and group
inheritance have been applied. It reads the file you name, so it shows what the
daemon would load from it. To see what a running daemon applied, use
show config running.";
                ze:help "Show the fully resolved configuration tree of a file.";
                leaf strip-private {
                    type empty;
                    description "Replace every sensitive value in the answer with a marker, so the tree
can be shared without its secrets.";
                    ze:help "Replace sensitive values with a marker.";
                }
            }

            container running {
                config false;
                ze:command "ze-config:show-config-running";
                description "The running daemon answers with the configuration it applied, from
memory, not from a file. A reload the daemon refused leaves this answer
unchanged, while the config file already holds the refused text. Secret values
are replaced with a placeholder.";
                ze:help "Show the configuration the running daemon applied.";
            }

            container diff {
                config false;
                ze:command "ze-config-cli:show-config-diff";
                description "Shows what was added, removed, or changed. Commonly used with rollback
revisions to review what changed before you roll back.";
                ze:help "Compare two configuration versions side by side.";
            }

            container history {
                config false;
                ze:command "ze-config-cli:show-config-history";
                description "Shows revisions with timestamps and commit metadata. Pair with 'show config
diff' to review changes before rolling back.";
                ze:help "List available configuration rollback points.";
            }

            container list {
                config false;
                ze:command "ze-config-cli:show-config-list";
                description "Shows archived snapshots and the active config.";
                ze:help "List all configuration files stored in the database.";
            }

            container cat {
                config false;
                ze:command "ze-config-cli:show-config-cat";
                description "Outputs the config as-is.";
                ze:help "Print the full text of a stored configuration snapshot.";
                leaf id {
                    type string { length "1..128"; }
                    mandatory true;
                    description "The value is a key that show config list prints. Ze reads that file from
the configuration store and writes its bytes unchanged.";
                    ze:help "Stored configuration snapshot id.";
                }
            }

            container fmt {
                config false;
                ze:command "ze-config-cli:show-config-fmt";
                description "Normalizes indentation and ordering. Output goes to stdout (read-only). To
rewrite the file in place, use 'ze config fmt -w' from the CLI.";
                ze:help "Pretty-print the configuration with consistent formatting.";

                leaf check {
                    type empty;
                    description "Answers whether the file needs formatting instead of the formatted text:
exit 0 when it is formatted, 1 with the file named when it is not.";
                    ze:help "Report whether formatting is needed";
                }
                leaf diff {
                    type empty;
                    description "Answers the unified diff formatting would apply instead of the formatted
text.";
                    ze:help "Show what formatting would change";
                }
            }

            container graph {
                config false;
                ze:command "ze-config-cli:show-config-graph";
                description "Prints the dependency graph of a config file as JSON. Inactive blocks
are left out, so the graph is the one the daemon would build.";
                ze:help "Show how components and peers depend on each other, as JSON.";
                leaf file {
                    type string { length "1..4096"; }
                    mandatory true;
                    description "The config file to read, or - to read it on stdin.";
                    ze:help "Config file path, or - for stdin.";
                }
            }

            container validation {
                config false;
                ze:command "ze-config-cli:show-config-validation";
                description "Both the grammar of the file and the meaning of its values are checked,
and each problem is reported with the diagnostic code that explains it. Nothing is
applied.";
                ze:help "Check a config for errors without applying it.";
                leaf file {
                    type string { length "1..4096"; }
                    mandatory true;
                    description "The config file to check, or - to read it on stdin.";
                    ze:help "Config file path, or - for stdin.";
                }
            }
        }
    }
}
