module ze-debug-cmd {
    namespace "urn:ze:debug:cmd";
    prefix debugcmd;
    import ze-extensions { prefix ze; }
    description "Debug state: the live state the daemon reports, and the stored profile in debug.zefs that the set, delete and clear debug commands edit and show debug profile reads. Owned by the debug plugin, which registers every handler. See ai/rules/plugin-self-containment.md.";
    revision 2026-10-08 { description "Declare the debug profile commands the debug plugin already served: set debug, delete debug, clear debug and show debug profile."; }
    revision 2026-06-13 { description "Initial: show debug returns live slogutil levels, flags, and scopes."; }

    container show {
        config false;
        ze:help "Read-only commands to inspect system, protocol, and network state.";

        container debug {
            config false;
            ze:command "ze-debug:debug-state";
            description "Lists every registered subsystem with its current log level and any active
flag or scope filters. Unlike 'debug show' (which reads the stored profile),
this reflects actual runtime state.";
            ze:help "Show live debug state from the running daemon.";

            container profile {
                config false;
                ze:command "ze-debug:show-profile";
                description "Reads debug.zefs and asks no daemon. With no argument it lists the
profile names. name <name> prints that profile as a table of module, level, flags and
scopes, and module <prefix> then keeps the rows under one subsystem subtree. Any other
trailing word is refused rather than ignored.";
                ze:help "Show stored debug profiles, one by name, or one filtered to a module subtree.";
                leaf name {
                    type string;
                    description "The stored profile to print. Absent, the command lists the profile names.";
                    ze:help "Profile name.";
                }
                leaf module {
                    type string;
                    description "A subsystem prefix. Only the rows at or under that subtree are printed,
and the keyword is read only after name.";
                    ze:help "Subsystem subtree to keep.";
                }
            }
        }
    }

    container set {
        config false;

        container debug {
            config false;
            description "Each command edits the stored debug profile in debug.zefs, and the
commands that change the default slot apply it to the running daemon.";
            ze:help "Edit the stored debug profile.";

            container module {
                config false;
                ze:command "ze-debug:set-module";
                description "The bare command enables the subsystem at its default level. A level, a
flag or a scope narrows what the subsystem writes. The profile is saved and applied.";
                ze:help "Enable debug output for one subsystem.";
                leaf module-name {
                    type string;
                    mandatory true;
                    description "The subsystem name, as show debug lists it. A name holding a slash is
refused.";
                    ze:help "Subsystem name.";
                }
                leaf level {
                    type string;
                    description "One of disabled, debug, info, warn or error. Any other word is refused.";
                    ze:help "Log level for the subsystem.";
                }
                leaf flag {
                    type string;
                    description "A flag the subsystem declares. A flag it does not declare is refused and
the valid flags are listed.";
                    ze:help "Debug flag to enable.";
                }
                container scope {
                    config false;
                    ze:modifier "once";
                    description "Restricts the subsystem's output to one value of one scope kind, such as
one peer.";
                    ze:help "Scope filter to add.";
                    leaf kind {
                        type string;
                        mandatory true;
                        description "A scope kind the subsystem declares. An undeclared kind is refused.";
                        ze:help "Scope kind.";
                    }
                    leaf value {
                        type string;
                        mandatory true;
                        description "The value the output is restricted to, read as written.";
                        ze:help "Scope value.";
                    }
                }
            }

            container timeout {
                config false;
                ze:command "ze-debug:set-timeout";
                description "The duration is written as 30m, 1h or 90s. Seconds are rounded up to
minutes, the longest accepted value is 24h, and zero disables the timer.";
                ze:help "Set how long debug output stays enabled.";
                leaf duration {
                    type string;
                    mandatory true;
                    description "A duration such as 30m, 1h, 90s or 0.";
                    ze:help "How long debug stays enabled.";
                }
            }

            container profile {
                config false;
                description "Named debug profiles are stored beside the default slot in debug.zefs.";
                ze:help "Named debug profiles.";

                container name {
                    config false;
                    ze:command "ze-debug:set-profile-name";
                    description "It copies what the daemon is writing now into a named slot. The default
slot is left as it is, so saving a profile does not change what the running daemon logs.";
                    ze:help "Save the current debug state as a named profile.";
                    leaf profile-name {
                        type string;
                        mandatory true;
                        description "The slot the current state is saved under.";
                        ze:help "Profile name.";
                    }
                }
            }

            container active {
                config false;
                description "The profile the running daemon applies.";
                ze:help "Choose the live debug profile.";

                container name {
                    config false;
                    ze:command "ze-debug:set-active-name";
                    description "The named profile becomes the live state and the default slot is not
overwritten, so a restart returns the daemon to the default profile rather than to this one.";
                    ze:help "Load a named debug profile and apply it to the running daemon.";
                    leaf profile-name {
                        type string;
                        mandatory true;
                        description "A stored profile, as show debug profile lists it.";
                        ze:help "Profile name.";
                    }
                }
            }
        }
    }

    container delete {
        config false;

        container debug {
            config false;
            description "Each command removes from the stored debug profile in debug.zefs.";
            ze:help "Remove from the stored debug profile.";

            container module {
                config false;
                ze:command "ze-debug:delete-module";
                description "The module name alone removes the whole module. Naming a flag or a scope
removes that one and leaves the module enabled. Deleting a module the profile does not
hold succeeds and changes nothing, so a repeated command is safe.";
                ze:help "Disable debug for a subsystem, or remove one of its flags or scopes.";
                leaf module-name {
                    type string;
                    mandatory true;
                    description "The subsystem name, as show debug lists it.";
                    ze:help "Subsystem name.";
                }
                leaf flag {
                    type string;
                    description "The flag to remove. The module stays enabled.";
                    ze:help "Debug flag to remove.";
                }
                container scope {
                    config false;
                    ze:modifier "once";
                    description "The scope filter to remove. The module stays enabled.";
                    ze:help "Scope filter to remove.";
                    leaf kind {
                        type string;
                        mandatory true;
                        description "The scope kind of the filter.";
                        ze:help "Scope kind.";
                    }
                    leaf value {
                        type string;
                        mandatory true;
                        description "The value of the filter.";
                        ze:help "Scope value.";
                    }
                }
            }

            container profile {
                config false;
                description "Named debug profiles are stored beside the default slot in debug.zefs.";
                ze:help "Named debug profiles.";

                container name {
                    config false;
                    ze:command "ze-debug:delete-profile-name";
                    description "It removes the stored slot and nothing else. The running daemon keeps
whatever it is writing, so deleting the profile that is live does not turn its output off.";
                    ze:help "Delete a named debug profile.";
                    leaf profile-name {
                        type string;
                        mandatory true;
                        description "A stored profile, as show debug profile lists it.";
                        ze:help "Profile name.";
                    }
                }
            }
        }
    }

    container clear {
        config false;

        container debug {
            config false;
            ze:command "ze-debug:clear-debug";
            description "It writes an empty profile into the default slot and applies it, so the
stored default and the running daemon both stop. A named profile is not touched.";
            ze:help "Clear the default debug profile.";
        }
    }
}
