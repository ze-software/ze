module ze-schema-cli-cmd {
    namespace "urn:ze:schema:cli:cmd";
    prefix schemaclicmd;
    import ze-extensions { prefix ze; }
    description "show schema command tree. Owned by the config schema subsystem because these handlers inspect registered YANG schemas, RPCs, and events. See ai/rules/plugin-self-containment.md.";
    revision 2026-06-06 { description "Relocated show schema out of the central show schema (plugin self-containment)."; }

    container show {
        config false;
        ze:help "Read-only commands to inspect system, protocol, and network state.";

        container schema {
            config false;
            description "What is listed comes from the registries this binary links, so the answer depends
                         on the build and on which plugins loaded.";
            ze:help "Discover registered YANG schemas, RPCs, and events.";

            container list {
                config false;
                ze:command "ze-config-schema:show-schema-list";
                description "Shows module name, namespace, and revision for each schema.";
                ze:help "List all YANG schemas loaded by the daemon.";
            }

            container methods {
                config false;
                ze:command "ze-config-schema:show-schema-methods";
                description "Useful for plugin developers to discover available operations.";
                ze:help "List all RPC methods defined in YANG API modules.";
            }

            container events {
                config false;
                ze:command "ze-config-schema:show-schema-events";
                description "Shows which events a plugin can subscribe to.";
                ze:help "List all notification types defined in YANG API modules.";
            }

            container handlers {
                config false;
                ze:command "ze-config-schema:show-schema-handlers";
                description "Maps module names to their implementing Go handler.";
                ze:help "Show which handler serves each YANG module.";
            }

            container protocol {
                config false;
                ze:command "ze-config-schema:show-schema-protocol";
                description "Useful for checking compatibility between Ze versions.";
                ze:help "Show the wire protocol version and format details.";
            }
        }
    }
}
