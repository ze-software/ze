module ze-ntp-conf {
    namespace "urn:ze:ntp:conf";
    prefix ntp;

    import ze-extensions { prefix ze; }

    description "NTP client configuration for Ze";

    revision 2026-01-01 {
        description "Initial revision";
    }

    container environment {
        description "The environment tree holds the settings of the services Ze runs, beside
the routing configuration rather than inside it.";
        ze:help "Environment settings of the NTP client.";

        container ntp {
            description "The presence of these settings does not start the client. Set the
enabled leaf to true.";
            ze:help "Settings of the NTP client.";

            leaf enabled {
                type boolean;
                default false;
                description "The default is false, so Ze leaves the system clock alone until
this leaf is true.";
                ze:help "Synchronize the system clock with an NTP server.";
            }

            leaf interval {
                type uint32 {
                    range "60..86400";
                }
                default 3600;
                description "The range is 60 to 86400 seconds, and the default is 3600.";
                ze:help "Seconds between two clock synchronizations.";
            }

            leaf max-step {
                type uint32 {
                    range "0..86400";
                }
                default 3600;
                description "Ze refuses a step larger than this value, which keeps a wrong
server answer from moving the clock far. A value of 0 removes the limit, so Ze accepts
a step of any size.";
                ze:help "Largest clock step in seconds that Ze accepts.";
            }

            leaf slew-threshold {
                type uint32 {
                    range "0..1000";
                }
                default 128;
                description "Ze corrects an offset up to this threshold with Adjtimex, which slews
the clock gradually. Ze corrects a larger offset with Settimeofday, which steps the
clock. A value of 0 disables the slew, so Ze always steps the clock.";
                ze:help "Maximum offset in milliseconds for a gradual clock slew.";
            }

            leaf persist-path {
                type string;
                default "/perm/ze/timefile";
                description "Ze writes the current time to this file at shutdown, and reads it
at startup. The stored time gives the clock a sane value before the first NTP answer
arrives.";
                ze:help "Path of the file that holds the time across a restart.";
            }

            list server {
                key "name";
                description "The list key is the name leaf, so one entry exists for each
server.";
                ze:help "The NTP servers Ze queries.";

                leaf name {
                    type string;
                    description "The name identifies the entry in the configuration. It is not
the address Ze queries, which the address leaf holds.";
                    ze:help "Name of this server entry, which is the list key.";
                }

                leaf address {
                    type string;
                    description "The value is an IPv4 address, an IPv6 address, or a
hostname.";
                    ze:help "Hostname or IP address of the NTP server.";
                }
            }
        }
    }
}
