module ze-ntp-cmd {
    namespace "urn:ze:ntp:cmd";
    prefix ntpcmd;
    import ze-extensions { prefix ze; }
    // The handlers read NTP peer and sync state.
    // See ai/rules/plugin-self-containment.md.
    description "The show system ntp command tree, owned by the ntp plugin.";
    revision 2026-06-06 { description "Relocated show system ntp out of the central show schema (plugin self-containment)."; }

    container show {
        config false;
        ze:help "Read-only commands to inspect system, protocol, and network state.";

        container system {
            config false;

            container ntp {
                config false;
                description "The answer carries enabled false alone when NTP is off. It carries the
                             same when the daemon has recorded no state yet, so the two cases read
                             alike. An enabled client answers whether it is synced, its source, the
                             offset, the stratum and the poll interval. The last-sync time is
                             present only after a synchronization has happened.";
                ze:help "NTP clock synchronization status.";

                ze:command "ze-ntp:show-system-ntp";

                container peers {
                    config false;
                    ze:command "ze-ntp:show-system-ntp-peers";
                    description "Tells you whether your clock is synced and how far off each NTP server thinks
you are.";
                    ze:help "Show NTP peers with offset, RTT, stratum, and reachability.";
                }
            }
        }
    }
}
