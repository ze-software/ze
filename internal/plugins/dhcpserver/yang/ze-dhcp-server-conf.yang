module ze-dhcp-server-conf {
    namespace "urn:ze:dhcp-server:conf";
    prefix dhcpsrv;

    import ze-types { prefix zt; }
    import ze-extensions { prefix ze; }

    description
        "DHCP server configuration for Ze (RFC 2131/2132).
         Every address leaf is IPv4: this server speaks DHCPv4 only, and the
         reply builder narrows each address it sends to four bytes. The
         ze:validate annotations declare that family in the model. They do not
         enforce it today, because ValidateCustomSections walks a fixed list of
         top-level sections and `service` is not one of them, so parseSubnet in
         the plugin is what refuses an IPv6 address.";

    revision 2026-01-01 {
        description "Initial revision";
    }

    container service {
        description "The container holds the settings of each service Ze runs. The dhcp-server container under it
                     configures the DHCPv4 server.";
        // Several modules declare this container and the config tree merges them,
        // so this text states the same fact as ze-as112-conf in its own words.
        ze:help "Service settings";

        container dhcp-server {
            description "DHCP server settings. Ze speaks DHCPv4 only (RFC 2131 and RFC 2132), so every address leaf under
                         this container is IPv4. The server binds one listener for each name in listen-interface. A
                         listener answers a client no relay forwarded only from the shared networks that hold a
                         subnet its interface is addressed in, and a relayed client from the shared network that
                         holds the relay's address (giaddr).";
            ze:help "DHCP server settings";

            leaf enabled {
                type boolean;
                default false;
                description "Enable the DHCP server. Left false, the plugin still parses and validates the config, and it
                    binds no socket and builds no handler. A commit that sets it true rebuilds one handler for each
                    subnet and binds the listeners again.";
                ze:help "Enable DHCP server";
            }

            leaf-list listen-interface {
                type string;
                description "Interfaces to serve DHCP on. Ze binds one UDP listener for each name in the list. A name that
                    fails to bind is logged as an error and skipped. When no name binds, the server logs that it is
                    not serving and answers nothing.";
                ze:help "Interfaces to serve DHCP on";
            }

            container pxe {
                description "PXE boot server settings (RFC 4578). Ze adds these options only when the client vendor class
                        in option 60 starts with PXEClient:. An ordinary DHCP client sees none of them. With pxe
                        enabled, a commit also requires tftp-server, bootfile-bios and bootfile-uefi.";
                ze:help "PXE boot server settings (RFC 4578)";

                leaf enabled {
                    type boolean;
                    default false;
                    description "Enable PXE boot option injection. Set true, a commit also requires tftp-server,
                        bootfile-bios and bootfile-uefi, and it names the missing one. Left false, Ze adds no PXE
                        option even for a client that identifies itself as PXEClient.";
                    ze:help "Enable PXE boot option injection";
                }

                leaf tftp-server {
                    type string;
                    ze:validate "ipv4-address";
                    description "TFTP server IP address for PXE boot. Ze writes the address into the siaddr field of the
                        reply (RFC 2131 Section 4.3.1) and its text form into option 66 (RFC 2132 Section 9.9). The
                        address has to be IPv4. An iPXE client receives neither, because boot-script-url answers it
                        instead.";
                    ze:help "TFTP server IP address for PXE boot (option 66, siaddr)";
                }

                leaf bootfile-bios {
                    type string;
                    description "Boot file path for BIOS clients, sent as option 67. Ze sends it whenever the first client
                        architecture in option 93 is any value other than 7 (RFC 4578 Section 2.1). An absent or
                        malformed option 93 reads as architecture 0, which is BIOS, so this path is the fallback.";
                    ze:help "Boot file path for BIOS clients (option 67)";
                }

                leaf bootfile-uefi {
                    type string;
                    description "Boot file path for UEFI clients, sent as option 67. Ze sends it only when the first client
                        architecture in option 93 is 7, which is UEFI x64 (RFC 4578 Section 2.1). Every other
                        architecture receives bootfile-bios.";
                    ze:help "Boot file path for UEFI clients (option 67)";
                }

                leaf boot-script-url {
                    type string;
                    description "HTTP URL for the iPXE boot script. Ze sends it as option 67 only to a client whose user
                        class in option 77 starts with iPXE. That reply carries option 60 and option 67 alone, so
                        the iPXE client receives no option 66, no option 43 and no siaddr. A commit rejects a URL
                        that does not start with http:// or https://, and one longer than 255 characters.";
                    ze:help "HTTP URL for iPXE boot script (sent as option 67 to iPXE clients)";
                }
            }

            list shared-network {
                key "name";
                description "The subnets of one physical segment. The name is a label for the operator, and Ze puts it on no
                    packet. A static mapping in any subnet of the segment is offered before any pool, and a new
                    address comes from the subnet holding the listen interface's primary address (or the relay's
                    address), then from the other subnets in the order Ze sorts them: shared networks by name,
                    subnets by prefix text.";
                ze:help "Named network grouping of subnets";

                leaf name {
                    type string;
                    description "Shared network name, and the key of this list. Ze sorts the groups by this name. After the
                        subnet holding the listen interface's primary address (or the relay's address), the order
                        decides which pool a new address comes from next.";
                    ze:help "Shared network name";
                }

                list subnet {
                    key "prefix";
                    description "Subnet with address pool and options. Each subnet has its own address pool and lease
                        table. A request is served from the subnet the client belongs to on its segment: its static
                        mapping first, then its current binding, then the requested address when it is free, then
                        a pool. The listen interface needs an address in a subnet of the segment, unless the
                        request came through a relay.";
                    ze:help "Subnet with address pool and options";

                    leaf prefix {
                        type string;
                        ze:validate "ipv4-prefix";
                        description "Subnet prefix, and the key of this list. The prefix has to be IPv4, and a commit
                            rejects any other family. Ze tests each range address, each static mapping address and
                            the relay address of a request against this prefix. The prefix also gives the subnet
                            mask the reply carries in option 1.";
                        ze:help "Subnet prefix (e.g. 192.168.1.0/24)";
                    }

                    list range {
                        key "name";
                        description "Named dynamic address pool range. A subnet holds 10 ranges at most. Ze sorts them by
                            start address and rejects a commit where two of them overlap. Ze allocates in that
                            order.";
                        ze:help "Named dynamic address pool range";

                        leaf name {
                            type string;
                            description "Range name, and the key of this list. The name appears in the commit error that
                                reports an overlap, and on no packet. A start and a stop written with no name are
                                read as one range named default.";
                            ze:help "Range name";
                        }

                        leaf start {
                            type string;
                            ze:validate "ipv4-address";
                            description "First allocatable address, and the address is allocatable. It has to fall inside
                                the subnet prefix, and it has to be less than or equal to stop. A commit names which
                                of the two rules it broke.";
                            ze:help "First allocatable address";
                        }

                        leaf stop {
                            type string;
                            ze:validate "ipv4-address";
                            description "Last allocatable address, and the address is allocatable. It has to fall inside the
                                subnet prefix. A range of one address is written with the same value in start and
                                stop.";
                            ze:help "Last allocatable address";
                        }
                    }

                    leaf lease-time {
                        type uint32 {
                            range "60..604800";
                        }
                        default 86400;
                        description "Lease duration in seconds, 60 to 604800, default 86400. Ze sends it as option 51. It
                            also sends the renewal time T1 as half of it, and the rebinding time T2 as seven
                            eighths of it. RFC 2131 Section 4.4.5 states those two fractions. The lease table drops
                            a binding after the same time.";
                        ze:help "Lease duration in seconds";
                    }

                    leaf default-router {
                        type string;
                        ze:validate "ipv4-address";
                        description "Default gateway address, sent as option 3. It does not choose the server
                            identifier (option 54): see server-identifier.";
                        ze:help "Default gateway address (option 3)";
                    }

                    leaf server-identifier {
                        type string;
                        ze:validate "ipv4-address";
                        description "Address the server identifies itself with in this subnet's replies, sent as
                            option 54 and in siaddr unless PXE names a TFTP server. Left unset, Ze uses the listen
                            interface's address inside the subnet, or, for a subnet served only through a relay,
                            the interface's primary address. Set it to name one address when the interface holds
                            several in the subnet, such as a VRRP virtual address. A commit rejects a value that
                            is not a unicast host address, or that is the network or broadcast address of the
                            subnet. The address need not fall inside the subnet. When the listen interface does not
                            hold the address at the time of a request, Ze does not answer and logs a warning naming
                            the subnet, the address and the fix. A REQUEST naming any of the server's addresses on
                            the segment (RFC 2131 Section 4.1) is accepted as addressed to this server.";
                        ze:help "Server identifier address (option 54)";
                    }

                    leaf-list dns-server {
                        type string;
                        ze:validate "ipv4-address";
                        description "DNS server addresses, sent as option 6. Write them in preference order, because Ze
                            sends them in the order it reads them. A commit rejects more than 63 addresses, which is
                            what one DHCP option holds, and it rejects an address that is not IPv4.";
                        ze:help "DNS server addresses (option 6)";
                    }

                    uses zt:dns-source {
                        refine dns-source {
                            description "The sources of this subnet's option 6, in order. configured is dns-server;
                                received is every IPv4 resolver Ze learned by DHCPv4, IPCP or the host's own
                                resolv.conf; self is Ze's own address inside this subnet on the interface that
                                received the request, none for a relayed request. radius is refused here. A loopback
                                address is never handed out, whatever its source, and each one dropped is logged.
                                With the container absent the default is source configured, then received, mode
                                first-usable: the dns-server entries when any are set, otherwise the learned
                                resolvers. While the list reaches received and no received entry is usable, replies
                                carry a 60-second lease (a configured shorter lease is kept), so a client that leased
                                with the WAN down renews within a minute of it coming up. Write source configured
                                alone to keep a subnet with no dns-server from sending option 6.";
                        }
                    }

                    leaf domain-name {
                        type string;
                        description "Domain name for clients, sent as option 15. Ze sends the string as it is written. A
                            commit rejects a value longer than 255 characters, which is the most one DHCP option
                            holds.";
                        ze:help "Domain name for clients (option 15)";
                    }

                    list static-mapping {
                        key "name";
                        description "Static MAC-to-IP binding. Ze answers a client whose MAC address matches with the mapped
                            address, and it never consults the dynamic pool for that client. A mapped address that
                            falls inside a range is marked in the pool, so no other client is offered it.";
                        ze:help "Static MAC-to-IP binding";

                        leaf name {
                            type string;
                            description "Mapping name, and the key of this list. The name appears in the commit error that
                                reports a bad mapping, and on no packet. Ze sorts the mappings of a subnet by this
                                name.";
                            ze:help "Mapping name";
                        }

                        leaf mac-address {
                            type string;
                            description "Client MAC address. Ze reads the colon form aa:bb:cc:dd:ee:ff, the hyphen form and
                                the dotted form. Ze matches the value against the client hardware address of the
                                request. A mapping with no mac-address is rejected at commit.";
                            ze:help "Client MAC address (xx:xx:xx:xx:xx:xx)";
                        }

                        leaf ip-address {
                            type string;
                            ze:validate "ipv4-address";
                            description "Fixed IP address for this client. It has to fall inside the subnet prefix, and a
                                commit rejects an address outside it. The address does not have to fall inside a
                                range. When it does, Ze marks it allocated so the dynamic pool never offers it to
                                another client.";
                            ze:help "Fixed IP address for this client";
                        }
                    }
                }
            }
        }
    }
}
