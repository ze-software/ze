module ze-env-cmd {
    namespace "urn:ze:env:cmd";
    prefix envcmd;
    import ze-extensions { prefix ze; }
    description "show env command tree. Owned by core/env because these handlers read the environment variable registry. See ai/rules/plugin-self-containment.md.";
    revision 2026-08-29 { description "Declare the value the description spelled in prose, so the model states the grammar and the generated usage line reads it."; }
    revision 2026-06-06 { description "Relocated show env out of the central show schema (plugin self-containment)."; }

    container show {
        config false;
        ze:help "Read-only commands to inspect system, protocol, and network state.";

        container env {
            config false;
            description "It reports the variables Ze itself registered, with the value in force. A variable
                         the process inherited but Ze never declared is not listed.";
            ze:help "Ze environment variable inspection.";

            container list {
                config false;
                ze:command "ze-env:show-list";
                description "Shows which env vars are set and their defaults.";
                ze:help "List all Ze environment variables with their current values.";
            }

            container get {
                config false;
                ze:command "ze-env:show-get";
                description "Returns the variable name, current value, default, and what it controls.";
                ze:help "Show one environment variable in detail.";
                leaf name {
                    type string { length "1..128"; }
                    mandatory true;
                    description "The variable's full name as Ze registered it, matched exactly.
A name Ze never declared is refused, even when the process inherited it.";
                    ze:help "Environment variable name";
                }
            }

            container registered {
                config false;
                ze:command "ze-env:show-registered";
                description "Includes type, default, description, and whether it is currently set.";
                ze:help "List every registered environment variable with metadata.";
            }
        }
    }
}
