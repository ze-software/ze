module ze-isis-conf {
    namespace "urn:ze:isis:conf";
    prefix isisconf;
    import ze-extensions { prefix ze; }
    import ze-policy-conf { prefix policy; }
    description
        "Native IS-IS link-state IGP configuration (ISO/IEC 10589, RFC 1195,
         RFC 5305 wide metrics, RFC 5301 dynamic hostname, RFC 5304/5310
         authentication). Presence of the isis container enables the component.";
    revision 2026-06-18 { description "Initial revision (spec-isis-4)."; }
    revision 2026-08-10 { description "hostname: enforce RFC 5301 section 3 7-bit ASCII and the RFC 2181 section 11 label lengths (spec-fixit-isis-hostname-ascii)."; }

    container isis {
        uses policy:igp-filter;
        description "The presence of this container starts the IS-IS component. At least one `net` leaf MUST be set for
            the engine to run. A commit with no net is accepted, and the engine then stays idle, opens no circuit and
            originates no LSP.";
        ze:help "IS-IS routing instance configuration.";

        // ISO/IEC 10589 section 6.2: a NET is an Area Address (1..13 octets) +
        // the 6-octet System ID + a 1-octet NSEL of 0x00 for an IS. At least one
        // NET is required; the system-id is derived from the first NET's 6 bytes
        // before the NSEL. The custom validator enforces hex/length/NSEL.
        leaf-list net {
            type string;
            ze:validate "isis-net";
            description "Network Entity Title(s), for example 49.0001.0000.0000.0001.00. At least one is required. The System
                ID is the 6 octets before the NSEL.";
            ze:help "Network Entity Title(s) of this IS-IS instance, at least one.";
        }

        // RFC 1195: the System ID is a fixed 6-octet field. The pattern enforces
        // the canonical dotted-hex form xxxx.xxxx.xxxx; when omitted it is derived
        // from the NET.
        // RFC 7950 Section 7.5.4.1: "If the constraint evaluates to "false", the
        // string is passed as <error-message> in the <rpc-error> in NETCONF." The
        // pattern is the one guard on the form, so it carries the operator's
        // message. The ze:validate name below is completion-only and refuses
        // nothing.
        leaf system-id {
            type string {
                pattern "[0-9a-fA-F]{4}\\.[0-9a-fA-F]{4}\\.[0-9a-fA-F]{4}" {
                    error-message "An IS-IS system-id is 6 octets in hex, written as three groups of 4 hex digits, such as 0000.0000.0001. Write it in that form, or delete system-id so that Ze takes it from net.";
                }
            }
            ze:validate "isis-system-id";
            description "When this leaf is not set, Ze takes the System ID from the 6 octets before the NSEL of the first
                `net`. When it is set, the value MUST equal that derived value. A mismatch refuses the commit with
                'system-id does not match the system id derived from net'.";
            ze:help "6-byte System ID (xxxx.xxxx.xxxx); derived from NET if unset.";
        }

        leaf level {
            type enumeration {
                enum l1 { ze:help "Level-1 (intra-area) only."; }
                enum l2 { ze:help "Level-2 (backbone) only."; }
                enum l1-l2 { ze:help "Both Level-1 and Level-2."; }
            }
            default "l1-l2";
            description "l1 holds only the Level-1 database and keeps this IS inside its own area. l2 holds only the
                Level-2 database and makes this IS a backbone router. l1-l2, the default, holds both databases and
                originates one LSP set at each level. A circuit forms an adjacency only at a level this leaf keeps.";
            ze:help "Routing level of this Intermediate System.";
        }

        leaf lsp-lifetime {
            type uint16 { range "1..65535"; }
            default 1200;
            units seconds;
            description "The value stamps the Remaining Lifetime of every LSP this IS originates. A neighbor purges the
                LSP when that field reaches 0, so a refresh MUST land first. The default of 1200 seconds pairs with
                the 900-second refresh default. This value also bounds the refresh. A refresh of 0, or one
                that is not less than this value, falls back to half of it.";
            ze:help "Maximum LSP remaining lifetime.";
        }

        leaf lsp-refresh-interval {
            type uint16 { range "1..65535"; }
            default 900;
            units seconds;
            description "Ze re-originates its own LSP set at this period, which bumps the sequence number and resets the
                Remaining Lifetime to `lsp-lifetime`. Without the refresh a quiet node ages out of every neighbor's
                database and disappears from the topology. A value of 0, or a value that is not less than
                `lsp-lifetime`, falls back to half of `lsp-lifetime`. A refresh then always lands before the purge.";
            ze:help "LSP refresh interval.";
        }

        leaf overload {
            type boolean;
            default false;
            description "The bit goes into the type block of this node's own LSP number zero. RFC 3787 section 4 states
                that 'Section 7.2.8.1 of ISO 10589 instructs other systems not to use the overloaded IS as a transit
                router'. Ze's own SPF obeys the bit the same way. It settles an overloaded node, so the prefixes
                that node advertises stay reachable. It expands none of that node's links, so no path runs through
                the node. Set the bit to hold transit traffic away while BGP converges after a restart.";
            ze:help "Set the overload bit (RFC 3787).";
        }

        // RFC 3787 section 5: "If not all devices in the IS-IS domain support
        // wide metrics, narrow metrics MUST continue to be used." The parser
        // maps the token (parseMetricStyle), and validateMetricStyle refuses a
        // circuit metric above 63 under narrow or transition.
        leaf metric-style {
            type enumeration {
                enum narrow { ze:help "Narrow 6-bit metrics only (TLV 2, TLV 128)."; }
                enum transition { ze:help "Both narrow and wide metrics, for the migration."; }
                enum wide { ze:help "Wide metrics only (TLV 22, TLV 135)."; }
            }
            default "wide";
            description "The style picks the reachability TLVs of every LSP this IS originates, its pseudo-node LSPs
                included. wide, the default, writes the RFC 5305 TLV 22 and TLV 135 with their 24-bit and 32-bit
                metrics. narrow writes the TLV 2 and TLV 128 of ISO 10589 and RFC 1195, whose metric is 6 bits.
                transition writes both. RFC 3787 section 5 states that 'If not all devices in the IS-IS domain
                support wide metrics, narrow metrics MUST continue to be used', so set narrow while any router in
                the domain is narrow-only, and transition while the domain migrates. Under narrow and transition a
                circuit `metric` above 63 is refused. A prefix metric above 63, such as a redistributed route's, is
                advertised as 63 in TLV 128. IPv6 reachability stays in TLV 236 in every style.";
            ze:help "Metric style of the originated LSPs (RFC 3787 section 5).";
        }

        // RFC 5301 section 3: the dynamic hostname (TLV 137) advertised by this
        // IS. "The Value field is encoded in 7-bit ASCII" and "The content of
        // this value is a domain name, see [RFC2181]". The isis-hostname
        // validator enforces both: printable 7-bit ASCII octets, and the RFC
        // 2181 section 11 label lengths. It carries no `pattern` on purpose. A
        // pattern is applied on the config-file parse path, which aborts before
        // the custom validator runs, so it would replace an actionable error
        // with a regex.
        leaf hostname {
            type string { length "1..255"; }
            ze:validate "isis-hostname";
            description "Dynamic hostname to advertise (RFC 5301 section 3). Printable 7-bit ASCII only, from space (0x20) to
                tilde (0x7e). Each dot-separated label is 1 to 63 octets and the whole name is at most 255 octets,
                including the separators (RFC 2181 section 11). One trailing dot is permitted. A non-ASCII name is
                refused, not converted.";
            ze:help "Dynamic hostname this IS-IS instance advertises (RFC 5301 section 3).";
        }

        container interfaces {
            description "Only an interface with an entry here runs IS-IS. Ze opens no circuit on an interface that this
                list omits, so no adjacency forms on it and its connected prefixes reach no LSP.";
            ze:help "IS-IS-enabled interfaces.";
            list interface {
                key "name";
                description "Ze opens one circuit for each entry that is enabled and not passive. A link that comes up
                    after start opens its circuit at that moment, and a link that goes down closes it. The connected
                    prefixes of an enabled entry become TLV 135 and TLV 236 reachability in the node's own LSP.";
                ze:help "Per-interface IS-IS configuration.";

                leaf name {
                    type string;
                    description "The value MUST be the kernel interface name, for example eth0. Ze reads the interface
                        index, the source MAC address and the MTU from the transport under that name. Ze tracks no
                        circuit while the transport reports no interface under it.";
                    ze:help "Interface name.";
                }
                leaf enabled {
                    type boolean;
                    default true;
                    description "The default is true, so an entry runs IS-IS without this leaf. A false value keeps the
                        entry in the configuration and opens no circuit. It also stops the connected prefixes of the
                        interface from reaching the node's own LSP, which a passive interface still advertises.";
                    ze:help "IS-IS enabled on this interface.";
                }
                leaf passive {
                    type boolean;
                    default false;
                    description "Ze opens no circuit for a passive interface, so it sends no hello and forms no
                        adjacency. The connected prefixes of the interface still become TLV 135 and TLV 236 entries
                        in the node's own LSP, at the metric `metric` sets. Use it on a loopback and on a customer
                        LAN, where the prefix MUST be reachable and no IS-IS neighbor exists.";
                    ze:help "Advertise the interface but form no adjacencies.";
                }
                leaf circuit-type {
                    type enumeration {
                        enum broadcast { ze:help "LAN broadcast circuit (DIS election)."; }
                        enum point-to-point { ze:help "Point-to-point circuit."; }
                    }
                    default "broadcast";
                    description "broadcast, the default, runs the DIS election and sources a pseudo-node LSP when this
                        IS wins. It advertises the LAN as one TLV 22 entry that points at the pseudo-node. It also
                        sources a periodic CSNP while this IS is DIS. point-to-point runs no election and no
                        pseudo-node. It sends a point-to-point hello with TLV 240 and one initial CSNP when the
                        adjacency reaches Up.";
                    ze:help "Circuit type.";
                }
                leaf level {
                    type enumeration {
                        enum l1 { ze:help "Form only a Level-1 adjacency on this circuit."; }
                        enum l2 { ze:help "Form only a Level-2 adjacency on this circuit."; }
                        enum l1-l2 { ze:help "Form both adjacencies on this circuit, the default."; }
                    }
                    default "l1-l2";
                    description "This narrows the instance `level` for one circuit. l1 forms only a Level-1 adjacency on
                        the circuit, l2 only a Level-2 adjacency, and l1-l2 forms both. The circuit floods LSPs and
                        advertises its reachability only at the levels it forms. A level the instance `level` does
                        not hold stays off whatever this leaf says.";
                    ze:help "Per-interface level override.";
                }
                // RFC 5305: wide metric, 24-bit (TLV 22) / 32-bit (TLV 135). The
                // per-interface circuit metric is bounded to the 24-bit wide range;
                // under a narrow or transition metric-style validateMetricStyle
                // bounds it to the 6-bit narrow range (1..63).
                leaf metric {
                    type uint32 { range "1..16777215"; }
                    default 10;
                    description "The circuit advertises this cost in TLV 22, and its connected prefixes advertise it in
                        TLV 135 and TLV 236. RFC 5305 section 3 states that 'The metric octets are encoded as a
                        24-bit unsigned integer', which is the 1 to 16777215 range here. Under the narrow and
                        transition `metric-style` the cost also goes into TLV 2 and TLV 128, whose metric is 6 bits,
                        so a value above 63 is refused there. SPF adds the value once for each hop, so a lower value
                        makes the circuit preferred. `level-1/metric` and `level-2/metric` replace it at one level.";
                    ze:help "Circuit metric (RFC 5305 wide, 1 to 63 when narrow).";
                }
                leaf hello-interval {
                    type uint16 { range "1..65535"; }
                    default 10;
                    units seconds;
                    description "Ze sends an IIH on this circuit at this period. The IIH carries a holding time of this
                        value multiplied by `hold-multiplier`, clamped into 1 to 65535 seconds. A neighbor drops the
                        adjacency when no IIH arrives inside the holding time it was told. A shorter interval detects
                        a dead neighbor faster and costs more packets on the link. `level-1/hello-interval` and
                        `level-2/hello-interval` replace it at one level.";
                    ze:help "Hello interval.";
                }
                leaf hold-multiplier {
                    type uint8 { range "1..255"; }
                    default 3;
                    description "Ze advertises `hello-interval` multiplied by this value as the holding time in each IIH,
                        clamped into 1 to 65535 seconds. The default of 3 lets two hellos be lost before a neighbor
                        drops the adjacency. The clamp means that no configuration can advertise a holding time of 0,
                        which would time the adjacency out at once. `level-1/hold-multiplier` and
                        `level-2/hold-multiplier` replace it at one level.";
                    ze:help "Hold time = hello-interval * hold-multiplier.";
                }
                leaf priority {
                    type uint8 { range "0..127"; }
                    default 64;
                    description "The value rides in each LAN hello and decides the DIS election on a broadcast circuit.
                        The highest priority wins, and the highest SNPA MAC address breaks a tie. A priority of 0 is
                        valid and only lowers the preference, so it does not stop this IS from winning an election it
                        is alone in. The leaf changes nothing on a point-to-point circuit.";
                    ze:help "DIS election priority (broadcast circuits).";
                }

                container level-1 {
                    description "The leaves here replace the circuit-wide value for Level-1 only. One circuit can then
                        carry a different cost, a different DIS preference, a different Hello period or a different
                        holding time at each level. A leaf that is not set keeps the circuit-wide value. A circuit
                        that does not form Level-1 ignores the whole container.";
                    ze:help "Level-1 per-interface overrides.";
                    leaf metric {
                        type uint32 { range "1..16777215"; }
                        description "Ze advertises this cost for the circuit in the Level-1 LSP, in place of `metric`. An
                            unset leaf keeps the circuit-wide metric. The value also becomes the metric of the
                            connected prefixes the circuit contributes at Level-1. Under the narrow and
                            transition `metric-style` a value above 63 is refused.";
                        ze:help "L1 metric override.";
                    }
                    leaf hello-interval {
                        type uint16 { range "1..65535"; }
                        units seconds;
                        description "Ze sends the Level-1 IIH at this period, in place of the circuit-wide
                            `hello-interval`. A broadcast circuit runs one Hello timer for each level it forms,
                            because the Level-1 and the Level-2 LAN IIH are separate PDUs sent to separate multicast
                            groups. A point-to-point circuit sends one IIH that serves both levels, so it runs one
                            Hello timer, and that timer takes this pair whenever the circuit forms Level-1. An unset
                            leaf keeps the circuit-wide value.";
                        ze:help "L1 hello-interval override.";
                    }
                    leaf hold-multiplier {
                        type uint8 { range "1..255"; }
                        description "Ze multiplies the Level-1 hello interval by this value and advertises the product as
                            the holding time in each Level-1 IIH, clamped into 1 to 65535 seconds. It replaces the
                            circuit-wide `hold-multiplier` for Level-1. An unset leaf keeps the circuit-wide value.";
                        ze:help "L1 hold-multiplier override.";
                    }
                    leaf priority {
                        type uint8 { range "0..127"; }
                        description "Ze uses this priority in the Level-1 DIS election, in place of `priority`. An unset
                            leaf keeps the circuit-wide priority, and so does the value 0: Ze reads an override only
                            when it is more than 0. To ask for the lowest preference, set the circuit-wide `priority`
                            to 0.";
                        ze:help "L1 DIS priority override.";
                    }
                    leaf auth-key-chain {
                        type leafref {
                            path "../../../../key-chains/name";
                        }
                        description "The value names a `key-chains` entry. Ze then signs and verifies the Level-1 IIH on
                            this circuit with that chain. RFC 5304 section 2 states that 'IS-IS Hello PDUs SHALL use
                            the Link Level Authentication String'. This leaf covers the hello only. The LSP, CSNP and
                            PSNP take the chain that `isis/level-1/auth-key-chain` names.";
                        ze:help "L1 per-interface (IIH) key-chain reference.";
                    }
                }
                container level-2 {
                    description "The leaves here replace the circuit-wide value for Level-2 only. One circuit can then
                        carry a different cost, a different DIS preference, a different Hello period or a different
                        holding time at each level. A leaf that is not set keeps the circuit-wide value. A circuit
                        that does not form Level-2 ignores the whole container.";
                    ze:help "Level-2 per-interface overrides.";
                    leaf metric {
                        type uint32 { range "1..16777215"; }
                        description "Ze advertises this cost for the circuit in the Level-2 LSP, in place of `metric`. An
                            unset leaf keeps the circuit-wide metric. The value also becomes the metric of the
                            connected prefixes the circuit contributes at Level-2. Under the narrow and
                            transition `metric-style` a value above 63 is refused.";
                        ze:help "L2 metric override.";
                    }
                    leaf hello-interval {
                        type uint16 { range "1..65535"; }
                        units seconds;
                        description "Ze sends the Level-2 IIH at this period, in place of the circuit-wide
                            `hello-interval`. A broadcast circuit runs one Hello timer for each level it forms,
                            because the Level-1 and the Level-2 LAN IIH are separate PDUs sent to separate multicast
                            groups. A point-to-point circuit sends one IIH that serves both levels, so it runs one
                            Hello timer, and that timer takes this pair only on a circuit that forms Level-2 alone.
                            An unset leaf keeps the circuit-wide value.";
                        ze:help "L2 hello-interval override.";
                    }
                    leaf hold-multiplier {
                        type uint8 { range "1..255"; }
                        description "Ze multiplies the Level-2 hello interval by this value and advertises the product as
                            the holding time in each Level-2 IIH, clamped into 1 to 65535 seconds. It replaces the
                            circuit-wide `hold-multiplier` for Level-2. An unset leaf keeps the circuit-wide value.";
                        ze:help "L2 hold-multiplier override.";
                    }
                    leaf priority {
                        type uint8 { range "0..127"; }
                        description "Ze uses this priority in the Level-2 DIS election, in place of `priority`. An unset
                            leaf keeps the circuit-wide priority, and so does the value 0: Ze reads an override only
                            when it is more than 0. To ask for the lowest preference, set the circuit-wide `priority`
                            to 0.";
                        ze:help "L2 DIS priority override.";
                    }
                    leaf auth-key-chain {
                        type leafref {
                            path "../../../../key-chains/name";
                        }
                        description "The value names a `key-chains` entry. Ze then signs and verifies the Level-2 IIH on
                            this circuit with that chain. RFC 5304 section 2 states that 'IS-IS Hello PDUs SHALL use
                            the Link Level Authentication String'. This leaf covers the hello only. The LSP, CSNP and
                            PSNP take the chain that `isis/level-2/auth-key-chain` names.";
                        ze:help "L2 per-interface (IIH) key-chain reference.";
                    }
                }

                list address-family {
                    key "af";
                    description
                        "An ipv6-unicast entry enables the interface's IPv6 addresses
                         and prefixes. On any enabled interface it also adds IPv6 to
                         the node-wide Protocols Supported set in every Hello and LSP.
                         IPv4 is always supported. Both families use one SPF tree.";
                    ze:help "Enable address families on this interface.";
                    leaf af {
                        type enumeration {
                            enum ipv4-unicast { ze:help "IPv4 unicast."; }
                            enum ipv6-unicast { ze:help "IPv6 unicast."; }
                        }
                        description "The value is the list key, so one entry names one family.
                                     The ipv6-unicast entry is what turns IPv6 on for the
                                     circuit. TLV 232 then carries the link-local address of
                                     the interface, and the circuit originates its IPv6
                                     prefixes in TLV 236.";
                        ze:help "Address family key.";
                    }
                }
            }
        }

        list key-chains {
            key "name";
            description "A chain holds the keys that sign and verify IS-IS PDUs. Ze authenticates nothing until an
                `auth-key-chain` leaf names the chain. Commit refuses an `auth-key-chain` leaf that
                names no entry of this list, naming the chains that exist, because a circuit whose chain does not resolve sends and accepts every
                PDU unsigned. A key whose algorithm token Ze does not know, or whose secret does not decode, is
                dropped from the chain and signs nothing.";
            ze:help "Named authentication key chains for hitless key rotation.";
            leaf name {
                type string { length "1..63"; }
                description "The name is the value an `auth-key-chain` leaf carries, at the instance level and on each
                    circuit. One chain CAN serve both levels and every circuit at the same time.";
                ze:help "Key-chain name; referenced by per-interface and per-level auth leaves.";
            }
            list key {
                key "key-id";
                description "Ze reads the keys in configuration order, which is key-id order. The first key whose send
                    lifetime holds the current time signs a PDU. Every key whose accept lifetime holds that time is
                    accepted on receive, up to 16 keys, which is what makes a rotation lose no adjacency.";
                ze:help "Keys in this chain.";
                leaf key-id {
                    type uint16 { range "0..65535"; }
                    description "RFC 5310 section 2 calls the Key ID 'a two-octet unsigned integer used to uniquely
                        identify an IS-IS SA'. The same section states that 'The receiver determines the active SA by
                        looking at the Key ID field in the incoming PDU'. Both ends of an adjacency MUST hold the
                        same key-id for the same secret. When this leaf is absent, Ze takes the value from the list
                        key.";
                    ze:help "Key identifier carried in TLV 10 (RFC 5310).";
                }
                leaf algorithm {
                    type enumeration {
                        enum cleartext { ze:help "Cleartext password (auth type 1)."; }
                        enum hmac-md5 { ze:help "HMAC-MD5 (auth type 54, RFC 5304)."; }
                        enum hmac-sha-1 { ze:help "HMAC-SHA-1 (auth type 3, RFC 5310)."; }
                        enum hmac-sha-224 { ze:help "HMAC-SHA-224 (auth type 3, RFC 5310)."; }
                        enum hmac-sha-256 { ze:help "HMAC-SHA-256 (auth type 3, RFC 5310)."; }
                        enum hmac-sha-384 { ze:help "HMAC-SHA-384 (auth type 3, RFC 5310)."; }
                        enum hmac-sha-512 { ze:help "HMAC-SHA-512 (auth type 3, RFC 5310)."; }
                    }
                    default "hmac-md5";
                    description "cleartext sends the secret in the PDU as auth type 1, so it detects a misconfiguration
                        and stops no attacker. hmac-md5, the default, is auth type 54 (RFC 5304). The five SHA
                        choices are auth type 3 (RFC 5310) and range from HMAC-SHA-1 to HMAC-SHA-512. Ze drops a key
                        whose token it does not know, so a typo here leaves that key out of the chain.";
                    ze:help "Authentication algorithm.";
                }
                leaf secret {
                    type string { length "1..255"; }
                    ze:sensitive;
                    description "The commit encodes the value with the reversible $9$ encoding, the same one PPPoE and
                        WireGuard use, and the configuration output masks it. Ze decodes it in memory to derive the
                        HMAC key. A value that does not decode drops the key from the chain. Both ends of an
                        adjacency MUST hold the same plaintext secret under the same key-id.";
                    ze:help "Shared secret, masked and $9$-encoded at rest.";
                }
                container send-lifetime {
                    description "Ze signs with the first key in the chain whose send window holds the current time. A key
                        with no send-lifetime signs from the moment it is committed. When no key in the chain has an
                        open send window, Ze sends the PDU unsigned, and a neighbor under authentication rejects it.";
                    ze:help "When this key may be used to sign (hitless rotation).";
                    leaf start {
                        type string;
                        description "The format is RFC 3339, for example 2026-01-01T00:00:00Z. An empty value leaves the
                            start open. A value Ze cannot parse also leaves the start open, and it does not drop the
                            key.";
                        ze:help "RFC3339 start timestamp.";
                    }
                    leaf end {
                        type string;
                        description "The format is RFC 3339, for example 2026-06-01T00:00:00Z. An empty value leaves the
                            end open, so the key signs forever. Set the end of the old key after the start of the new
                            one, so the two windows overlap and the rotation loses no adjacency.";
                        ze:help "RFC3339 end timestamp.";
                    }
                }
                container accept-lifetime {
                    description "Ze accepts a received PDU signed with any key whose accept window holds the current
                        time, up to 16 keys in one chain. Open the accept window of the new key before its send
                        window. Every neighbor then accepts the new key before any of them signs with it.";
                    ze:help "When this key is accepted on receive (hitless rotation).";
                    leaf start {
                        type string;
                        description "The format is RFC 3339, for example 2026-01-01T00:00:00Z. An empty value leaves the
                            start open, so the key is accepted from the moment it is committed. A value Ze cannot
                            parse also leaves the start open.";
                        ze:help "RFC3339 start timestamp.";
                    }
                    leaf end {
                        type string;
                        description "The format is RFC 3339, for example 2026-06-01T00:00:00Z. An empty value leaves the
                            end open. Keep the accept window of the old key open until every neighbor signs with the
                            new key.";
                        ze:help "RFC3339 end timestamp.";
                    }
                }
            }
        }

        container level-1 {
            description "The leaves here apply to Level-1 across the whole instance, and not to one circuit. RFC 5304
                section 2 calls the key they select the Area Authentication string.";
            ze:help "Level-1 (area) per-level configuration.";
            leaf auth-key-chain {
                type leafref {
                    path "../../key-chains/name";
                }
                description "The value names a `key-chains` entry. Ze then signs and verifies every Level-1 LSP, CSNP and
                    PSNP with that chain. RFC 5304 section 2 states that 'Level 1 Sequence Number PDUs SHALL use the
                    Area Authentication string as in Level 1 Link State PDUs'. The IIH is separate and takes the
                    per-interface chain.";
                ze:help "L1 per-level (LSP/SNP, area key) key-chain reference.";
            }
        }
        container level-2 {
            description "The leaves here apply to Level-2 across the whole instance, and not to one circuit. RFC 5304
                section 2 calls the key they select the domain authentication string.";
            ze:help "Level-2 (domain) per-level configuration.";
            leaf auth-key-chain {
                type leafref {
                    path "../../key-chains/name";
                }
                description "The value names a `key-chains` entry. Ze then signs and verifies every Level-2 LSP, CSNP and
                    PSNP with that chain. RFC 5304 section 2 states that 'Level 2 Sequence Number PDUs SHALL use the
                    domain authentication string as in Level 2 Link State PDUs'. The IIH is separate and takes the
                    per-interface chain.";
                ze:help "L2 per-level (LSP/SNP, domain key) key-chain reference.";
            }
        }
    }
}
