module ze-isis-cmd {
    namespace "urn:ze:isis:cmd";
    prefix isiscmd;
    import ze-extensions { prefix ze; }
    // Removing the component removes these command nodes together with the
    // handlers in internal/plugins/isis/cmd_show.go. Both verbs bind into the
    // CENTRAL ze-show and ze-clear command namespaces, which are the
    // Go-registered RPCs and the LDP/iface model, so there is no per-component
    // ze-isis-api module. The show and clear subtrees container-merge onto the
    // generic show and clear verb roots.
    // See ai/rules/plugin-self-containment.md.
    description "The show isis and clear isis command tree, owned by the isis component.";
    // show isis neighbor, database[ detail], route, interface, hostname and
    // spf-log, and clear isis adjacency all and counters.
    revision 2026-10-17 {
        description "clear isis adjacency alone is refused; clear isis adjacency all tears down every adjacency.";
    }
    revision 2026-06-18 {
        description "Initial revision: the show isis and clear isis commands (spec-isis-13).";
    }

    container show {
        config false;
        ze:help "Read-only commands to inspect system, protocol, and network state.";

        container isis {
            config false;
            description "The IS-IS commands read the state ISO/IEC 10589 and RFC 1195
define: the neighbors, the link-state database, the routes, the interfaces, the
hostnames, and the SPF history.";
            ze:help "IS-IS neighbors, database, routes, interfaces, hostnames, and SPF history.";

            container neighbor {
                config false;
                ze:command "ze-isis:show-neighbor";
                description "Returns the neighbor System ID, interface, level, adjacency state, and hold
time for each IS-IS neighbor.";
                ze:help "Show IS-IS adjacencies.";
            }

            container database {
                config false;
                ze:command "ze-isis:show-database";
                description "Lists each LSP with its LSP ID, sequence number, remaining lifetime, checksum,
and overload bit, across Level-1 and Level-2. The own field is true on the
LSPs this node originated and false on the LSPs it learned from a neighbor.";
                ze:help "Show the IS-IS link-state database.";

                container detail {
                    config false;
                    ze:command "ze-isis:show-database-detail";
                    description "Expands each LSP into its decoded TLVs (type, length, value) so you can read
exactly what each node advertises. It carries the same fields as the summary
view, the own field included.";
                    ze:help "Show the IS-IS link-state database with TLV detail.";
                }
            }

            container route {
                config false;
                ze:command "ze-isis:show-route";
                description "Lists each prefix the SPF installed with its metric, level, up/down bit, and
next-hops (address and outgoing interface).";
                ze:help "Show IS-IS-computed routes.";

                container ipv6 {
                    config false;
                    ze:command "ze-isis:show-route-ipv6";
                    description "Lists each IPv6 prefix the SPF installed with its metric, level, and next-hops
(link-local address and outgoing interface).";
                    ze:help "Show IS-IS-computed IPv6 routes (RFC 5308).";
                }
            }

            container interface {
                config false;
                ze:command "ze-isis:show-interface";
                description "Returns level, circuit type, metric, hello interval, hold multiplier, passive
flag, DIS state, and the count of Up adjacencies per circuit.";
                ze:help "Show IS-IS-enabled circuits.";
            }

            container hostname {
                config false;
                ze:command "ze-isis:show-hostname";
                description "Maps each System ID to the hostname it advertises in TLV 137.";
                ze:help "Show the IS-IS dynamic-hostname mapping (RFC 5301).";
            }

            container spf-log {
                config false;
                ze:command "ze-isis:show-spf-log";
                description "Returns the most recent SPF runs with their timestamp, level, trigger,
duration, and node count.";
                ze:help "Show recent IS-IS SPF runs.";
            }
        }
    }

    container clear {
        config false;

        container isis {
            config false;
            description "Adjacencies drop and counters zero. The configuration is untouched, so the router
                         rebuilds the same adjacencies it had.";
            ze:help "Reset IS-IS runtime state without reconfiguring.";

            container adjacency {
                config false;
                description "clear isis adjacency alone is refused: say all to tear down every
adjacency. Everything is never the default.";
                ze:help "Tear down IS-IS adjacencies: all.";

                container all {
                    config false;
                    ze:command "ze-isis:clear-adjacency";
                    description "Adjacencies re-learn from the next Hello; the circuit is not closed and the
configuration is unchanged.";
                    ze:help "Tear down every IS-IS adjacency so neighbors re-form.";
                }
            }

            container counters {
                config false;
                ze:command "ze-isis:clear-counters";
                description "Monotonic Prometheus series are not reset; the SPF-run history is cleared.";
                ze:help "Reset IS-IS observational counters and the SPF log.";
            }
        }
    }
}
