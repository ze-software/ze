module ze-kernel-conf {
    namespace "urn:ze:kernel:conf";
    prefix kernel;

    import ze-extensions { prefix ze; }

    description
        "Kernel route redistribution for Ze.
         When present, externally-installed kernel routes (DHCP, PPP,
         manual) are advertised into BGP via the redistribute event bus.";

    revision 2026-05-15 {
        description "Initial revision.";
    }

    container kernel {
        description "The container carries no leaf, so writing it is the whole configuration.
                     The plugin watches the kernel routing table and emits each route on the
                     redistribute event bus. A route whose netlink protocol is RTPROT_KERNEL or
                     RTPROT_REDIRECT is dropped, so a connected subnet route and an ICMP
                     redirect route never reach BGP. The plugin registers the kernel route
                     source, and a redistribute statement names that source.";
        ze:help "Kernel route redistribution. Presence enables the plugin.";
    }
}
