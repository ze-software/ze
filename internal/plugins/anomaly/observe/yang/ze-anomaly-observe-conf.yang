module ze-anomaly-observe-conf {
  namespace "urn:ze:anomaly-observe-conf";
  prefix anomaly-observe;

  import ze-anomaly-detect-conf { prefix ad; }
  import ze-extensions { prefix ze; }

  description "Behavioral anomaly incident lifecycle configuration. Augments the
               shared `anomaly` container (owned by ze-anomaly-detect-conf) with
               the `observe` subtree, the way `shape` augments the same parent.";
  revision 2026-08-17 { description "Nest under anomaly/observe: augment /ad:anomaly with container observe."; }

  augment "/ad:anomaly" {
    container observe {
      description "The store keeps each confirmed incident from its start to its end. `show anomaly observe` reads the
          store, so it can report the duration of a finished incident.";
      ze:help "Incident lifecycle store for confirmed anomaly incidents.";

      leaf incident-ring-size {
        type uint32 { range "1..100000"; }
        default 1000;
        description "When the ring is full, the oldest finalized incident is dropped first.";
        ze:help "Maximum number of incidents the ring keeps in memory.";
      }
      leaf stale-incident-timeout {
        type uint32 { range "1..86400"; }
        default 3600;
        description "The detector stops reporting an entity that goes idle, and it sends no clear event for that entity.
            This timeout is the limit on how long such an incident reads as active.";
        ze:help "Seconds before an open incident with no clear event is finalized.";
      }
    }
  }
}
