module ze-anomaly-observe-cmd {
    namespace "urn:ze:anomaly-observe:cmd";
    prefix anomalyobservecmd;
    import ze-extensions { prefix ze; }
    // The plugin holds the incident lifecycle store, so removing the plugin
    // removes this node and its handler together. The command container-merges
    // onto the shared `anomaly` namespace that `show anomaly detect` and
    // `show anomaly shape` also merge onto. See ai/rules/plugins.md.
    description "The show anomaly observe command tree, owned by the anomaly-observe plugin.";
    revision 2026-08-17 { description "Initial: show anomaly observe."; }

    container show {
        config false;
        ze:help "Read-only commands to inspect system, protocol, and network state.";

        container anomaly {
            config false;
            // Repeat the canonical description owned by ze-anomaly-cmd.yang
            // verbatim, because the command-tree merge keeps the first text.
            description "Detection and response are separate: the detector reports what it sees, and a
                         responder acts on it only where one is configured. A detected anomaly is not
                         itself a mitigation.";
            ze:help "Behavioral anomaly detection and response subsystem.";

            container observe {
                config false;
                ze:command "ze-anomaly:show-observe";
                description "Per incident: the source entity, cohort, fired features with their
deviation z-scores, combined score, severity, start time, end time, and whether
it is still active. Finalized incidents stay in the list, so this shows a
finished incident's duration, which `show anomaly detect` cannot.";
                ze:help "Show the behavioral anomaly incident lifecycle, newest first.";
            }
        }
    }
}
