module ze-anomaly-cmd {
    namespace "urn:ze:anomaly:cmd";
    prefix anomalycmd;
    import ze-extensions { prefix ze; }
    description "show anomaly detect command tree. Owned by the anomaly-detect plugin. Container-merges onto the shared `anomaly` namespace.";
    revision 2026-07-02 { description "Nest under show anomaly detect (was show anomaly); anomaly becomes a namespace shared with show anomaly shape."; }

    container show {
        config false;
        ze:help "Read-only commands to inspect system, protocol, and network state.";

        container anomaly {
            config false;
            description "Detection and response are separate: the detector reports what it sees, and a
                         responder acts on it only where one is configured. A detected anomaly is not
                         itself a mitigation.";
            ze:help "Behavioral anomaly detection and response subsystem.";

            container detect {
                config false;
                ze:command "ze-anomaly:show-anomaly";
                description "Each incident carries the source entity, the cohort, the fired
features with their deviation z-scores, the combined score, and the severity.
The detector only reports. The anomaly shape responder (Spec 2b) acts on the
report.";
                ze:help "Show the recent behavioral anomaly incidents.";
            }
        }
    }
}
