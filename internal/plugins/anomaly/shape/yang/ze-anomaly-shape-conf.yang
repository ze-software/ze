module ze-anomaly-shape-conf {
  namespace "urn:ze:anomaly-shape-conf";
  prefix anomaly-shape;

  import ze-types { prefix zt; }
  import ze-anomaly-detect-conf { prefix ad; }
  import ze-extensions { prefix ze; }

  description "Anomaly responder (shape) configuration. Augments the shared
               `anomaly` container (owned by ze-anomaly-detect-conf) with the
               `shape` subtree.";
  revision 2026-07-02 { description "Nest under anomaly/shape: augment /ad:anomaly with container shape."; }

  augment "/ad:anomaly" {
    container shape {
      description "The responder reads the incidents the detect subtree publishes,
                   and it acts on a source incident alone. In armed mode it writes an
                   nftables table named ze_anomaly-shape, with one term for each
                   armed source. The chain of that table attaches to the input hook
                   at priority -200, so it acts on the traffic addressed to this
                   host.";
      ze:help "Autonomous responder: shadow (log-only) or armed (live per-source firewall actions).";

      leaf mode {
        type enumeration {
          enum shadow { ze:help "Log the action the responder would take and install nothing."; }
          enum armed { ze:help "Install live per-source firewall actions."; }
        }
        default shadow;
        description "shadow, the default, logs the action it would take and installs
                     nothing. armed installs live per-source firewall actions.";
        ze:help "Responder mode: shadow or armed.";
      }
      leaf action {
        type enumeration {
          enum limit { ze:help "Rate-limit the source prefix at limit-rate per limit-unit."; }
          enum drop { ze:help "Discard every packet from the source prefix."; }
        }
        default limit;
        description "limit writes an nftables counter and a rate limit on the source
                     prefix, and it reads limit-rate, limit-unit and limit-burst.
                     drop writes a counter and discards every packet from that
                     source. Ze applies the action to each armed source, and it
                     applies nothing while mode is shadow.";
        ze:help "Armed action: rate-limit the source (surgical) or drop it (fallback).";
      }
      leaf limit-rate {
        type uint64 { range "1..max"; }
        default 1000;
        description "The rate counts packets, and limit-unit gives the time. The
                     default 1000, with the default unit second, lets 1000 packets a
                     second through from each armed source. A value of 0 is refused
                     at commit while the action is limit. The leaf changes nothing
                     while the action is drop.";
        ze:help "Rate for the limit action, in packets per limit-unit.";
      }
      leaf limit-unit {
        type enumeration {
          enum second { ze:help "Allow limit-rate packets each second."; }
          enum minute { ze:help "Allow limit-rate packets each minute."; }
          enum hour { ze:help "Allow limit-rate packets each hour."; }
          enum day { ze:help "Allow limit-rate packets each day."; }
        }
        default second;
        description "The unit divides limit-rate. A rate of 1000 with the unit minute
                     lets 1000 packets a minute through. Ze gives the word to the
                     nftables limit expression, and a word outside the four is
                     refused at commit. The leaf changes nothing while the action is
                     drop.";
        ze:help "Time unit for limit-rate.";
      }
      leaf limit-burst {
        type uint32;
        default 0;
        description "The burst is the number of packets Ze lets through above the
                     rate before it starts to drop. The default 0 gives no
                     allowance, so the rate applies from the first packet. Ze gives
                     the value to the nftables limit expression. The leaf changes
                     nothing while the action is drop.";
        ze:help "Burst allowance for the limit action.";
      }
      leaf auto-revert-ttl {
        type uint16 { range "5..3600"; }
        default 300;
        description "This ceiling holds whether or not a clear event arrives, so an
                     armed action can never stay in place indefinitely.";
        ze:help "Seconds after the last signal before an armed action reverts by itself.";
      }
      leaf blast-radius-cap {
        type uint16 { range "1..1024"; }
        default 16;
        description "Ze counts the sources that carry a live action. At this cap Ze
                     refuses to arm one more source, writes a warning, and raises the
                     arm-refused metric. A source that is armed already costs the
                     count nothing, because that path only refreshes its
                     auto-revert-ttl. The cap bounds the firewall table an incident
                     storm can produce.";
        ze:help "Maximum concurrently-armed live actions; further arm attempts are refused.";
      }
      leaf kill-switch {
        type boolean;
        default false;
        description "Ze runs the revert when it reads the config, so it also removes
                     what an earlier instance of the responder left in the firewall.
                     The responder then answers every incident as shadow does, and it
                     writes a log line in place of a rule. Set the leaf back to false
                     to let the responder arm again.";
        ze:help "When true, revert every armed action and force the responder to shadow.";
      }
      leaf-list allowlist {
        type zt:ip-prefix;
        description "The list guards against self-lockout, for management sources
                     and control-plane sources.";
        ze:help "Protected source prefixes that ze never arms an action against.";
      }
    }
  }
}
