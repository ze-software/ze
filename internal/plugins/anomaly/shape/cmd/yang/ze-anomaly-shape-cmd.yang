module ze-anomaly-shape-cmd {
    namespace "urn:ze:anomaly-shape:cmd";
    prefix anomalyshapecmd;
    import ze-extensions { prefix ze; }
    description "show anomaly shape command tree. Owned by the anomaly-shape plugin. Container-merges onto the shared `anomaly` namespace.";
    revision 2026-07-02 { description "Nest under show anomaly shape (was show anomaly-shape)."; }

    container show {
        config false;
        ze:help "Read-only commands to inspect system, protocol, and network state.";

        container anomaly {
            config false;
            // Repeat the canonical description owned by ze-anomaly-cmd.yang
            // verbatim, because the command-tree merge keeps the first text.
            description "Detection and response are separate: the detector reports what it sees, and a
                         responder acts on it only where one is configured. A detected anomaly is not
                         itself a mitigation.";
            ze:help "Behavioral anomaly detection and response subsystem.";

            container shape {
                config false;
                ze:command "ze-anomaly:show-shape";
                description "Returns the mode (shadow or armed), the action, and the kill-switch
state. It also returns the armed source entities with their live firewall
actions.";
                ze:help "Show the shadow-first anomaly responder status.";
            }
        }
    }
}
