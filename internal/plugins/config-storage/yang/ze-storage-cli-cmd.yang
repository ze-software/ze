module ze-storage-cli-cmd {
    namespace "urn:ze:storage:cli:cmd";
    prefix storageclicmd;
    import ze-extensions { prefix ze; }
    description "Commands to inspect stored keys and values. Owned by the config storage subsystem. See ai/rules/plugins.md.";
    revision 2026-08-31 { description "Renamed show data ls to show data list, so every command that enumerates a set spells the verb the same way."; }
    revision 2026-08-29 { description "Declare the value the description spelled in prose, so the model states the grammar and the generated usage line reads it."; }
    revision 2026-06-06 { description "Relocated show data out of the central show schema (plugin self-containment)."; }

    container show {
        config false;
        ze:help "Read-only commands to inspect system, protocol, and network state.";

        container data {
            config false;
            description "Inspect logical storage keys and their values. Use show config to read the configuration itself.";
            ze:help "Storage keys and values.";

            container list {
                config false;
                ze:command "ze-config-storage:show-data-list";
                description "Lists the keys in the selected store. Use 'show data cat <key>' to read one value.";
                ze:help "List the keys in the selected store.";
            }

            container cat {
                config false;
                ze:command "ze-config-storage:show-data-cat";
                description "Outputs the decoded value for the given storage key.";
                ze:help "Print the value of a storage key.";
                leaf key {
                    type string { length "1..512"; }
                    mandatory true;
                    description "The key of one entry, as show data list prints it. The bytes stored
                                 under it are written out unchanged, and a key the store does not
                                 hold is an error.";
                    ze:help "Storage key to print";
                }
            }

            container registered {
                config false;
                ze:command "ze-config-storage:show-data-registered";
                description "Lists the storage key patterns registered by subsystems.";
                ze:help "List the key patterns registered by all subsystems.";
            }
        }
    }
}
