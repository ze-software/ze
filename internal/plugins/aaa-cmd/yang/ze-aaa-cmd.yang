module ze-aaa-cmd {
    namespace "urn:ze:aaa:cmd";
    prefix aaacmd;
    import ze-extensions    { prefix ze; }
    import ze-cli-show-cmd  { prefix clishowcmd; }
    description "AAA show commands: accounting counters and dropped record visibility.
         Relocated from the central show schema for plugin self-containment.";
    revision 2026-06-03 { description "Initial revision: relocated from ze-cli-show-cmd."; }

    augment "/clishowcmd:show" {
        container aaa {
            config false;
            description "The view covers the AAA clients Ze talks to, RADIUS and TACACS+, rather than the
                         operator accounts on the box.";
            ze:help "Authentication, authorization, and accounting state.";
            container accounting {
                config false;
                ze:command "ze-aaa:show-accounting";
                description "Tells you whether TACACS+ accounting is working or if records are being lost
due to server unreachability.";
                ze:help "Show AAA accounting counters and any dropped records.";
            }
        }
    }
}
