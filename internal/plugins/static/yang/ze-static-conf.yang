module ze-static-conf {
    namespace "urn:ze:static:conf";
    prefix static;

    import ze-extensions { prefix ze; }
    import ze-policy-conf { prefix policy; }

    description
        "Static route configuration for Ze.
         Routes are programmed directly to the kernel (netlink) or VPP
         dataplane. Multiple next-hops produce ECMP with optional
         per-next-hop weights. BFD profiles enable fast failover.
         Routes are grouped under named tables (resolved via the
         routing-table registry). The 'default' table maps to the
         kernel main table (254).";

    revision 2026-05-15 {
        description "Add table grouping and interface-only next-hops.";
    }

    revision 2026-04-23 {
        description "Initial revision.";
    }

    container static {
        uses policy:rib-import-filter;
        description "Ze programs each route into the kernel through netlink, or into the VPP dataplane, and
            marks it with the static protocol number. A route the backend cannot program is skipped and
            logged, and the rest of the section still applies. Only a forward route in the default table
            reaches the redistribute bus, where BGP can announce it.";
        ze:help "Static route configuration.";

        list table {
            key "name";
            description "A named routing table grouping. The table name is resolved to a kernel table ID through the
                routing-table registry. Use 'default' for the main routing table.";
            ze:help "A named routing table that holds static routes.";

            leaf name {
                type string;
                description
                    "Ze resolves the name through the routing-table registry, and it stops the config
                    load for a name the registry does not hold. default and an empty name both resolve
                    to table 0, which the kernel reads as the main table. A route in any other table is
                    never redistributed.";
                ze:help "Table name. Must match an entry in the
                         routing-table registry, or 'default' for
                         the main table.";
            }

            list route {
                key "prefix";
                description "The prefix is the key, so one table holds one entry for each prefix. Ze compares
                    every leaf of the entry at a reload, the description included, and reprograms the
                    route when one of them changed.";
                ze:help "A static route entry.";

                leaf prefix {
                    type string;
                    ze:validate "ipv4-prefix|ipv6-prefix";
                    description "Ze masks the host bits, so 10.0.0.1/24 is stored and shown as 10.0.0.0/24.
                        The prefix is the list key, so it stands after the route keyword and not inside
                        the braces. Ze names the prefix in the error when it cannot parse it.";
                    ze:help "Destination prefix in CIDR notation.";
                }

                leaf description {
                    type string { length "0..255"; }
                    description "The note reaches show static routes and nothing else. It is not sent to the
                        kernel, and no filter reads it. Ze compares the note at a reload, so a change to
                        the note alone reprograms the route. The length is 0 to 255 characters.";
                    ze:help "Operator note for this route.";
                }

                leaf metric {
                    type uint32;
                    default 0;
                    description
                        "Ze writes the value into the netlink route priority. The kernel prefers the
                        lower priority when two routes cover the same prefix. 0 leaves the attribute
                        out, so the kernel applies its own default. The redistribute event carries the
                        same value.";
                    ze:help "Route metric. Used as kernel route priority
                             (lower is preferred) and carried in redistribute.";
                }

                leaf distance {
                    type uint8;
                    description "Ze ranks this route at the value against every other protocol's route for
                        the same prefix, in place of the distance rib distance static declares. The value
                        applies to this route alone. Lower wins, and 0 is the best rank. Without the leaf
                        the route ranks at the declared static distance, and a reload that changes the
                        declaration re-ranks it.";
                    ze:help "Administrative distance for this route alone (overrides rib distance static).";
                }

                leaf tag {
                    type uint32;
                    description "Ze prints the value in the tag field of show static route and in the config
                        diff. A redistribute import rule can select routes by tag: write the same value in
                        a tag leaf under redistribute destination <proto> import static. When Ze
                        redistributes the route into OSPF, it writes the value into the External Route Tag
                        of the AS-external LSA, and the tag on the route wins over the tag configured for
                        the source. Ze writes the value into no kernel route, because Linux has no route
                        tag attribute. A change to tag alone re-applies the route, because the config diff
                        compares the field.";
                    ze:help "Opaque tag Ze attaches to this route for policy and redistribution.";
                }

                choice action {
                    mandatory true;
                    description "One case is required. Ze stops the load for a route that names none of next,
                        blackhole and reject, and it names the prefix in the error. Only the forward case
                        reaches the redistribute bus.";
                    ze:help "What to do with matching packets.";

                    case forward {
                        description "The case holds the next container, which carries gateway next hops and
                            interface next hops. Two or more next hops of either kind become one ECMP
                            route. A redistribute consumer sees this case alone.";
                        ze:help "Send the packet on toward a next hop.";

                        container next {
                            description
                                "Ze reads the hop list and the interface list, and joins the two into
                                one set of next hops. A route whose next container holds neither one
                                stops the config load. One next hop becomes a plain route, and two or
                                more become a multipath route.";
                            ze:help "Forward action. Contains gateway and interface
                                     next-hops that may be combined for ECMP.";

                            list hop {
                                key "address";
                                description
                                    "The gateway address is the key, so one route holds one entry for
                                    each gateway. Ze shares the traffic between the entries in proportion
                                    to their weights. An entry can name its own BFD profile, and a next
                                    hop whose BFD session goes down leaves the group.";
                                ze:help "Forward via gateway. Multiple entries produce
                                         ECMP with traffic distributed by weight.";

                                leaf address {
                                    type string;
                                    ze:validate "ipv4-address|ipv6-address";
                                    description "The address is the list key, so it names the entry. Ze sets
                                        it as the netlink gateway, and the kernel selects the outgoing
                                        interface unless the interface leaf names one. IPv4 and IPv6 are
                                        both accepted.";
                                    ze:help "Gateway address.";
                                }

                                leaf interface {
                                    type string;
                                    description
                                        "Ze resolves the name to a kernel interface index and sets it
                                        on the route. A link-local IPv6 gateway needs it, because the
                                        same address can exist on every link. A name that resolves to no
                                        interface skips this one route, which show static routes then
                                        reports with its reason.";
                                    ze:help "Outgoing interface. Required when the
                                             next-hop is a link-local IPv6 address.";
                                }

                                leaf weight {
                                    type uint16 { range "1..65535"; }
                                    default 1;
                                    description "ECMP weight. A higher value receives proportionally more traffic. The default of 1 gives equal
                                        distribution.";
                                    ze:help "ECMP weight of this next-hop, 1 by default.";
                                }

                                leaf bfd-profile {
                                    type string;
                                    ze:reference "bfd-profile";
                                    description "BFD profile name (from bfd/profile list). When the BFD session to this next-hop goes down, Ze
                                        removes the next-hop from the ECMP group. Ze then reprograms the route with the remaining active
                                        next-hops. Commit, ze config validate and a SIGHUP reload refuse a name no bfd profile defines,
                                        naming the profiles that exist; the editor completes those names. The leaf names a list of
                                        another module that a build without BFD leaves out, so it is a ze:reference, not a leafref.
                                        The session is single-hop, so a commit is also refused when the profile sets passive
                                        (RFC 5881 Section 3).";
                                    ze:help "BFD profile name for this next-hop, from the bfd/profile list.";
                                }
                            }

                            list interface {
                                key "name";
                                description "Forward through the interface only, with no gateway address. This form serves point-to-point links,
                                    such as PPPoE and GRE tunnels, where the next-hop is implicit. Multiple entries can coexist with
                                    gateway next-hops for mixed ECMP.";
                                ze:help "Forward through the interface only, with no gateway address.";

                                leaf name {
                                    type string;
                                    description "The name is the list key, so it names the entry. This form
                                        serves a point-to-point link, where the packet needs no gateway
                                        address. A BFD profile is refused here, because a BFD session
                                        needs a peer address.";
                                    ze:help "Outgoing interface name.";
                                }

                                leaf weight {
                                    type uint16 { range "1..65535"; }
                                    default 1;
                                    description
                                        "The range is 1 to 65535, and Ze reads 0 as 1. The weight
                                        counts only against the other next hops of the same route. A
                                        route with one next hop ignores it.";
                                    ze:help "ECMP weight. Higher values receive
                                             proportionally more traffic.";
                                }
                            }
                        }
                    }

                    case discard {
                        description "The case holds the blackhole container, and the presence of that
                            container selects the action. Ze installs the route with the kernel blackhole
                            type, so the kernel drops the packet and answers nothing.";
                        ze:help "Drop the packet and tell the sender nothing.";

                        container blackhole {
                            presence "Silently discard matching packets.";
                            description "The sender sees a timeout rather than a refusal, so a traceroute
                                         stops at this hop with no reply. Use reject when the sender
                                         SHOULD learn the destination is unreachable.";
                            ze:help "Drop the packet and send no ICMP message to the sender.";
                        }
                    }

                    case unreachable {
                        description "The case holds the reject container, and the presence of that container
                            selects the action. Ze installs the route with the kernel unreachable type,
                            so the kernel answers with ICMP destination unreachable.";
                        ze:help "Drop the packet and answer the sender.";

                        container reject {
                            presence
                                "Discard and reply ICMP unreachable.";
                            description "The sender learns at once rather than waiting for a timeout, which
                                         is what separates this from blackhole. The reply itself costs a
                                         packet per dropped packet.";
                            ze:help "Drop the packet and send an ICMP unreachable to the sender.";
                        }
                    }
                }
            }
        }
    }
}
