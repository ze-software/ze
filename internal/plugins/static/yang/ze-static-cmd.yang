module ze-static-cmd {
    namespace "urn:ze:static:cmd";
    prefix staticcmd;
    import ze-extensions { prefix ze; }
    // Removing the plugin removes the command node together with the handler.
    // See ai/rules/plugin-self-containment.md.
    description "The show static command tree, owned by the static plugin.";
    revision 2026-06-03 { description "Relocated show static out of the central show schema (plugin self-containment)."; }

    container show {
        config false;
        ze:help "Read-only commands to inspect system, protocol, and network state.";

        container static {
            config false;
            ze:command "ze-static:show-static";
            description "Lists each static route with its prefix, next-hop, and interface.";
            ze:help "Show static routes defined in the configuration.";
        }
    }
}
