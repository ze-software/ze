module ze-fib-conf {
    namespace "urn:ze:fib:conf";
    prefix fib;

    import ze-extensions { prefix ze; }

    description
        "FIB configuration for Ze.
         Contains the kernel backend configuration for route programming.
         Admin distance settings are in ze-rib-conf (RIB concept).";

    revision 2026-04-04 {
        description "Move admin-distance to ze-rib-conf.";
    }

    container fib {
        description "The FIB is where Ze writes the best routes the system RIB chose.
                     Each container under it is one backend: kernel programs the OS with
                     netlink, and vpp programs VPP with the GoVPP binary API. A backend
                     runs only while its plugin is loaded. Admin distance is not here,
                     because it belongs to the rib container.";
        ze:help
            "Forwarding Information Base configuration.";

        container kernel {
            description "Ze writes each best route from the system RIB into the OS with
                         netlink, and it stamps rtm_protocol 250 on every route it
                         writes. That number separates a ze route from a route another
                         daemon owns, so `ip route show proto 250` lists them. The plugin
                         also watches the kernel, and it writes its route again where
                         something else overwrote one of them.";
            ze:help
                "OS kernel route programming via netlink (Linux).";

            leaf flush-on-stop {
                type boolean;
                default false;
                description
                    "When true, the plugin removes every route it installed as it
                     stops. The default false keeps those routes in the kernel
                     after shutdown, which supports graceful restart.";
                ze:help
                    "Remove every ze-installed route when the plugin stops.";
            }

            leaf sweep-delay {
                type uint16;
                default 30;
                units seconds;
                description
                    "The delay lets BGP reconverge and refresh the matching routes
                     before Ze removes the stale ones. The default is 30 seconds.";
                ze:help
                    "Time to wait after startup before Ze sweeps stale routes.";

            }
        }
    }
}
