module ze-ldp-cmd {
    namespace "urn:ze:ldp:cmd";
    prefix ldpcmd;
    import ze-extensions { prefix ze; }
    description "show ldp ... command tree. Owned by the ldp component so that removing it removes these command nodes together with the handlers. See ai/rules/plugin-self-containment.md.";
    revision 2026-06-03 { description "Relocated show ldp ... out of the central show schema (plugin self-containment)."; }

    container show {
        config false;
        description "Read-only commands to inspect system, protocol, and network state";

        container ldp {
            config false;
            description "LDP neighbors and label bindings";

            container neighbor {
                config false;
                ze:command "ze-show:ldp-neighbor";
                description "Show LDP neighbors and their session state.
Returns peer address, transport address, session state, and
hold time for each LDP neighbor.";
            }

            container binding {
                config false;
                ze:command "ze-show:ldp-binding";
                description "Show LDP FEC-to-label bindings.
Lists local and remote label bindings for each FEC (prefix).
Use this to verify label distribution is working.";
            }
        }
    }
}
