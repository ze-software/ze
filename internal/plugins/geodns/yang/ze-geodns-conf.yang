module ze-geodns-conf {
    namespace "urn:ze:geodns:conf";
    prefix geodns;

    import ze-types { prefix zt; }
    import ze-extensions { prefix ze; }

    description
        "GeoDNS server configuration for Ze: DNS answers are selected by the
         client source IP (RFC 1035 records, RFC 7871 EDNS0 client-subnet).
         Ported from the EXA SurfProtect geodns daemon; the per-source host
         files become YANG host-sets referenced by source prefixes.";

    revision 2026-06-26 {
        description "Initial revision";
    }

    container service {
        description "The container holds the settings of each service Ze runs, and the geodns container under it
            configures the GeoDNS server.";
        ze:help "Service settings";

        container geodns {
            description "GeoDNS answers a query from the client address rather than from the name alone. A `source`
                entry maps a client prefix to a `host-set`, and the longest prefix that holds the client address
                wins. The same name can then answer a different address to each client. Ze is authoritative for the
                `zone` entries only, and it serves no AXFR.";
            ze:help "GeoDNS server: per-source-IP DNS answers";

            leaf enabled {
                type boolean;
                default false;
                description "The default is false, so geodns binds no listener and answers no query. A true value binds
                    each `listener` entry for UDP and TCP, and it binds the DoT and DoH listeners that are enabled.
                    A false value unbinds every listener.";
                ze:help "Enable the GeoDNS server";
            }

            list listener {
                key "name";
                ze:listener;
                description "UDP+TCP listen endpoints. Each named entry binds one IP (IPv4 or IPv6) and one port. Repeat the same
                    port for a dual-stack pair. Ze defaults to 127.0.0.1:5300 and ::1:5300 when no entry is configured.
                    The ze:listener marking enables config-time port-conflict detection across services.";
                ze:help "UDP and TCP listen endpoints for geodns.";

                leaf name {
                    type string {
                        length "1..255";
                    }
                    description "The name is the key of the entry and nothing else reads it. Ze binds the `ip` and
                        `port` of each entry, in name order. Use a name that says what the endpoint is for, for
                        example v4-public or v6-loopback.";
                    ze:help "Listener instance name";
                }

                uses zt:listener {
                    refine ip {
                        default "127.0.0.1";
                    }
                    refine port {
                        default 5300;
                    }
                }
            }

            leaf default-ttl {
                type uint32 {
                    range "1..2147483647";
                }
                default 300;
                description "Default record TTL (seconds) when a host omits its own. The range is 1 to 2147483647 (RFC 2181
                    section 8). A zero default is not allowed.";
                ze:help "Default record TTL in seconds when a host omits its own.";
            }

            leaf client-ip-source {
                type enumeration {
                    enum edns0 {
                        ze:help "Use only the EDNS0 client-subnet option (RFC 7871); no answer without it";
                    }
                    enum packet {
                        ze:help "Use the UDP/TCP packet source IP";
                    }
                    enum edns0-then-packet {
                        ze:help "Prefer EDNS0 client-subnet, fall back to the packet source IP";
                    }
                }
                default "edns0-then-packet";
                description "edns0-then-packet, the default, reads the address from the EDNS0 client-subnet option (RFC
                    7871) and falls back to the packet source address. packet ignores the option and always reads the
                    packet source. edns0 reads only the option. A query with no option then matches no `source`
                    prefix, so a name the zone owns draws an empty NOERROR answer.";
                ze:help "Where the client IP used for source selection is read from";
            }

            leaf-list zone {
                type string {
                    length "1..255";
                }
                description "Zones served (FQDN). A query name must be one of these, or a name inside one, compared label by
                    label. A name outside every zone draws REFUSED.";
                ze:help "Zones served, as fully qualified domain names.";
            }

            leaf-list nameserver {
                type zt:ipv4-address;
                max-elements 9;
                description "Ze builds one NS record for each entry, named ns1.<zone> to nsN.<zone> in list order, and
                    one A glue record beside it. The glue name is synthesized and never configured. A commit is
                    refused when a zone is long enough to make nsN.<zone> break the length bounds RFC 1035 sets.
                    The records go in the Answer of an NS query and in the Authority of every other answer.";
                ze:help "Nameserver IPv4 addresses; ns1..nsN.<zone> A glue is synthesised (max 9)";
            }

            container soa {
                description "Ze builds the SOA record of each zone from these leaves. It serves no AXFR, so no secondary
                    acts on `refresh`, `retry` and `expire`, and those three only carry their value in the record.
                    `minimum` is the one field an answer depends on, because Ze stamps it as the TTL of the SOA
                    record and as its MINTTL.";
                ze:help "SOA record fields (synthesised; geodns serves no AXFR)";

                leaf mname {
                    type string {
                        length "1..255";
                    }
                    description "The value becomes the MNAME field of the SOA record. Ze adds the trailing dot when the
                        value has none. An unset leaf makes Ze build ns1.<zone> for each zone it serves, so the
                        name follows the zone the query asked for. A commit is refused when the name breaks the
                        length bounds RFC 1035 sets.";
                    ze:help "Primary nameserver (SOA MNAME). Defaults to ns1.<first-zone> when unset.";
                }
                leaf contact {
                    type string {
                        length "1..255";
                    }
                    default "hostmaster";
                    description "The value becomes the RNAME field of the SOA record. A value with no dot is read as the
                        mailbox local part under the zone, so the default builds hostmaster.<zone>. A value that
                        holds a dot is used as a whole domain name, with the trailing dot added.";
                    ze:help "Responsible-party mailbox label (SOA RNAME), e.g. hostmaster";
                }
                leaf serial-mode {
                    type enumeration {
                        enum auto-epoch {
                            ze:help "max(Unix seconds at commit, previous serial + 1); strictly increases at any rate";
                        }
                        enum auto-datetime {
                            ze:help "YYYYMMDDnn (RFC 1912); capped at 100 revisions/day by the 32-bit serial";
                        }
                        enum fixed {
                            ze:help "Use the serial leaf verbatim";
                        }
                    }
                    default "auto-epoch";
                    description "auto-epoch, the default, takes the Unix time in seconds at commit. It raises that by one
                        when the result is not more than the previous serial, so two commits in one second still
                        increase. auto-datetime builds YYYYMMDDnn (RFC 1912), and the 32-bit field leaves two counter
                        digits, so it holds 100 revisions in one day. fixed serves the `serial` leaf unchanged.";
                    ze:help "How the 32-bit SOA serial is generated";
                }
                leaf serial {
                    type uint32;
                    description "Ze reads this leaf only when `serial-mode` is fixed, and it then serves the value
                        unchanged. The other two modes compute the serial and ignore the leaf. In fixed mode you own
                        the increase after each change, under the serial arithmetic RFC 1982 defines.";
                    ze:help "SOA serial used when serial-mode is fixed";
                }
                leaf refresh {
                    type uint32;
                    default 3600;
                    description "The value goes into the REFRESH field of the SOA record, in seconds. It tells a
                        secondary how long to wait before it checks the serial again. geodns serves no AXFR, so no
                        secondary acts on it, and the value changes no answer Ze gives.";
                    ze:help "SOA refresh seconds";
                }
                leaf retry {
                    type uint32;
                    default 600;
                    description "The value goes into the RETRY field of the SOA record, in seconds. It tells a secondary
                        how long to wait after a failed refresh. geodns serves no AXFR, so no secondary acts on it,
                        and the value changes no answer Ze gives.";
                    ze:help "SOA retry seconds";
                }
                leaf expire {
                    type uint32;
                    default 300;
                    description "The value goes into the EXPIRE field of the SOA record, in seconds. It tells a secondary
                        when to stop the service of a zone it can no longer refresh. geodns serves no AXFR, so no
                        secondary acts on it, and the value changes no answer Ze gives.";
                    ze:help "SOA expire seconds";
                }
                leaf minimum {
                    type uint32 {
                        range "0..2147483647";
                    }
                    default 300;
                    description "SOA minimum, the negative-cache TTL in seconds. The range is 0 to 2147483647. The field is stamped
                        as the SOA record's own TTL, so the RFC 2181 section 8 TTL range bounds it.";
                    ze:help "SOA minimum, the negative-cache TTL in seconds.";
                }
            }

            list host-set {
                key "name";
                description "A host set is one answer set. Ze picks the set for a query from the client address, through
                    the `source` prefix that matches it. One set can serve several source prefixes. The same
                    hostname can appear in several sets with a different address in each. That is what makes the
                    answer depend on the client.";
                ze:help "Named, reusable set of host records; referenced by source entries";

                leaf name {
                    type string {
                        length "1..255";
                    }
                    description "The name is the value a `source/host-set` leaf carries. A commit is refused when a
                        source names a set that no entry here declares.";
                    ze:help "Host-set name (referenced by source/host-set)";
                }

                list host {
                    key "name";
                    description "One entry holds one name and the records Ze answers for it inside this set. A commit is
                        refused when the entry carries no address and `type` is not SRV. It is also refused when
                        `type` and the address family disagree.";
                    ze:help "A hostname and its records";

                    leaf name {
                        type string {
                            length "1..255";
                        }
                        description "The name MUST end in one of the `zone` entries, and a commit that breaks that is
                            refused. Ze adds the trailing dot when the value has none. The name also gives existence
                            to each node between it and the zone apex. A query for one of those parent names then
                            draws an empty NOERROR answer rather than NXDOMAIN.";
                        ze:help "Fully-qualified hostname (must end in a configured zone)";
                    }
                    leaf ttl {
                        type uint32 {
                            range "0..2147483647";
                        }
                        description "The value is the TTL in seconds of every record of this host. An unset leaf takes
                            `default-ttl`. 0 is permitted here and refused on `default-ttl`, and it asks a resolver
                            to cache the answer for no time. The range is the TTL range RFC 2181 section 8 sets.";
                        ze:help "Record TTL; defaults to default-ttl when unset";
                    }
                    leaf type {
                        type enumeration {
                            enum A { ze:help "Answer an A record for each address, and refuse an IPv6 address at commit."; }
                            enum AAAA { ze:help "Answer an AAAA record for each address, and refuse an IPv4 address at commit."; }
                            enum SRV { ze:help "Answer an SRV record from the srv container, and ignore the address list."; }
                        }
                        description "An unset leaf reads each `address` entry on its own, and answers A for an IPv4
                            address and AAAA for an IPv6 address. A refuses the commit for an IPv6 address, and AAAA
                            refuses it for an IPv4 address. SRV reads the `srv` container and ignores `address`.";
                        ze:help "Record type; omit to auto-detect A vs AAAA per address";
                    }
                    leaf-list address {
                        type zt:ip-address;
                        description "Each entry becomes one A record or one AAAA record for the host, and one query
                            answers all of them. Ze refuses the commit for a host with no entry here, unless `type`
                            is SRV.";
                        ze:help "One or more A/AAAA addresses (v4 => A, v6 => AAAA when type omitted)";
                    }
                    container srv {
                        description "Ze reads this container only when `type` is SRV. All four leaves are then required,
                            and a commit that omits one is refused with 'need priority weight port target'. An SRV
                            host answers one record, and `address` on it is ignored.";
                        ze:help "SRV record fields (when type is SRV)";
                        leaf priority {
                            type uint16;
                            description "RFC 2782 states that 'A client MUST attempt to contact the target host with the
                                lowest-numbered priority it can reach'. That text is in the section 'The format of
                                the SRV RR'. Targets that share a priority are ordered by `weight`. The range is 0
                                to 65535.";
                            ze:help "SRV priority";
                        }
                        leaf weight {
                            type uint16;
                            description "RFC 2782, 'The format of the SRV RR', calls the weight 'a relative weight for
                                entries with the same priority'. The same text states that 'Larger weights SHOULD be
                                given a proportionately higher probability of being selected'. Use 0 when one target
                                has no selection to do. The range is 0 to 65535.";
                            ze:help "SRV weight";
                        }
                        leaf port {
                            type uint16;
                            description "The value is the TCP or UDP port the service listens on at `target`. The range
                                is 0 to 65535. Ze copies the number into the record and checks nothing about it.";
                            ze:help "SRV port";
                        }
                        leaf target {
                            type string {
                                length "1..255";
                            }
                            description "The value is the hostname that runs the service. Ze adds the trailing dot when
                                the value has none. A commit is refused when the name breaks the length bounds RFC
                                1035 sets. Ze adds no address record for the target, so a client resolves that name
                                in a second query.";
                            ze:help "SRV target hostname";
                        }
                    }
                }
            }

            list source {
                key "prefix";
                description "Maps a client-IP prefix to a host-set. The longest prefix wins. 0.0.0.0/0 and ::/0 are the catch-all
                    external default.";
                ze:help "Maps a client-IP prefix to a host-set.";

                leaf prefix {
                    type zt:ip-prefix;
                    description "The prefix is the key of the entry. Ze masks it at commit, so 10.0.0.1/8 is stored as
                        10.0.0.0/8. The longest prefix that holds the client address wins, and a /32 or a /128 pins
                        one client. Add 0.0.0.0/0 and ::/0 to answer every client that no other prefix holds.";
                    ze:help "Client source prefix in CIDR (e.g. 82.219.0.0/16, 82.219.4.10/32, 0.0.0.0/0)";
                }
                leaf host-set {
                    type leafref {
                        path "../../host-set/name";
                        require-instance true;
                    }
                    description "The value names a `host-set` entry. The editor completes the configured sets, a commit
                        that names any other set is refused, and a source with no value here is refused as well. A
                        client this prefix matches is answered from that set alone.";
                    ze:help "Name of the host-set to answer for clients matching this prefix";
                }
            }

            container tls {
                description "DNS-over-TLS (DoT, RFC 7858) listener and the certificate material shared with DoH. When the
                    listener is enabled, DoT binds the configured listener IPs on 'listen-port'. When cert-file and
                    key-file are unset, Ze uses an ephemeral self-signed certificate, which a strict client cannot
                    validate.";
                ze:help "DNS-over-TLS listener and the certificate material shared with DoH.";

                leaf enabled {
                    type boolean;
                    default false;
                    description "The default is false, so geodns binds no DNS-over-TLS listener. A true value binds every
                        `listener` IP on `listen-port`, beside the cleartext endpoints. When the certificate material
                        does not load, Ze logs the error and starts no secure listener. The cleartext listeners stay
                        bound.";
                    ze:help "Enable the DNS-over-TLS listener (RFC 7858).";
                }

                leaf listen-port {
                    type zt:port;
                    default 853;
                    description
                        "The DoT listener binds this TCP port on every `listener` IP, and it uses no UDP. A
                        commit with the value 0 is refused. Move the port off 853 only when a client can be told the
                        new one, because a DoT client uses 853 by default.";
                    ze:help "TCP port for the DoT listener; the RFC 7858 well-known
                             'domain-s' port is 853.";
                }

                leaf cert-file {
                    type string;
                    description "Path to the PEM server certificate presented on DoT and DoH. Leave this leaf and key-file unset to
                        select an ephemeral self-signed certificate.";
                    ze:help "Path to the PEM server certificate presented on DoT and DoH.";
                }

                leaf key-file {
                    type string;
                    ze:sensitive;
                    description
                        "The value is the path to the PEM private key of `cert-file`, and the two go together.
                        Ze re-reads the pair on each commit, so a rotated key is picked up with no restart. This
                        leaf and `certificate` are mutually exclusive, and a commit that sets both is refused. Leave
                        both this leaf and `cert-file` unset to select an ephemeral self-signed certificate.";
                    ze:help "Path to the PEM private key matching cert-file. Must be
                             set together with cert-file.";
                }

                leaf certificate {
                    ze:reference "pki-certificate";
                    type string {
                        length "1..255";
                        pattern '[A-Za-z0-9._-]+';
                    }
                    description "Name of the certificate in the PKI store to serve on DoT and DoH. The listeners send the leaf
                        certificate and every intermediate certificate the store entry holds. This leaf and
                        cert-file/key-file are mutually exclusive, and setting both is a configuration error. The PKI store
                        lives in the hub process, so a geodns plugin started as an external process cannot resolve the name.
                        The secure listeners then do not start, and Ze logs the error. Cleartext DNS is unaffected.";
                    ze:help "Name of the PKI store certificate to serve on DoT and DoH.";
                }
            }

            container doh {
                description "DNS-over-HTTPS (DoH, RFC 8484) listener. It reuses the tls container's certificate material. It
                    binds the configured listener IPs on 'listen-port' at 'path'.";
                ze:help "DNS-over-HTTPS listener (DoH, RFC 8484).";

                leaf enabled {
                    type boolean;
                    default false;
                    description "The default is false, so geodns binds no DNS-over-HTTPS listener. A true value binds
                        every `listener` IP on `listen-port` at `path`. DoH takes the certificate material of the
                        `tls` container, so it needs no `tls/enabled`. A certificate that does not load starts no
                        secure listener, and the cleartext listeners stay bound.";
                    ze:help "Enable the DNS-over-HTTPS listener (RFC 8484).";
                }

                leaf listen-port {
                    type zt:port;
                    default 443;
                    description "The DoH listener binds this TCP port on every `listener` IP. A commit with the value 0
                        is refused. Move the port when a web server already holds 443 on the same address, because
                        the second bind of one address and port fails.";
                    ze:help "TCP port for the DoH HTTPS listener (RFC 8484).";
                }

                leaf path {
                    type string;
                    default "/dns-query";
                    description
                        "The DoH endpoint answers this path alone. An empty value keeps the default /dns-query.
                        RFC 8484 section 3 states that 'The DoH client is configured with a URI Template [RFC6570]'.
                        A client MUST therefore be told a path that is not the default.";
                    ze:help "HTTP request path the DoH endpoint answers on (RFC 8484
                             URI Template); defaults to /dns-query.";
                }
            }
        }
    }
}
