module ze-geodns-cmd {
    namespace "urn:ze:geodns:cmd";
    prefix geodnscmd;

    import ze-extensions { prefix ze; }

    description
        "show geodns command tree. Owned by the geodns plugin because the handler
         reads the geodns server's live state. See ai/rules/plugin-self-containment.md.";

    revision 2026-06-26 {
        description "Initial revision";
    }

    container show {
        config false;
        ze:help "Read-only commands to inspect system, protocol, and network state.";

        container geodns {
            config false;
            ze:command "ze-geodns:show-geodns";
            description "Returns whether the server is enabled, the bind addresses and
port, and the client-IP source mode. It also returns the zones, the nameserver,
host-set and source counts, and the current SOA serial.";
            ze:help "Show the GeoDNS server status.";
        }
    }
}
