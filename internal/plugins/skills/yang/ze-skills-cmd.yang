module ze-skills-cmd {
    namespace "urn:ze:skills:cmd";
    prefix skillscmd;
    import ze-extensions { prefix ze; }
    description "The show skills and show skill commands, and the commands that set an operator's agent up to use Ze (create, show and delete agent skill, show agent context), owned by the skills plugin, which registers their handlers. See the plugin self-containment rule.";
    revision 2026-11-14 { description "Declare create agent skill, show agent skill, delete agent skill and show agent context, each served by the plugin's own daemon command. delete agent skill with no agent acts on every harness found, as agent all does."; }
    revision 2026-11-02 { description "Declare the full flag show skill already read, so every route judges it against the model."; }
    revision 2026-10-12 { description "Rename skills list and skills get to show skills and show skill: the first word of a command is its verb."; }
    revision 2026-10-08 { description "Initial: declare the skills command the skills plugin already served."; }

    container show {
        config false;
        ze:help "Read-only commands to inspect system, protocol, and network state.";

        container skills {
            config false;
            ze:command "ze-skills:show-skills";
            description "Each skill is a Markdown document bundled with the binary, so it always
matches the running version. Prints each bundled skill with its one-line description.";
            ze:help "List the agent skills this binary carries.";
        }

        container skill {
            config false;
            ze:command "ze-skills:show-skill";
            description "Prints the named skill's Markdown document.";
            ze:help "Fetch one bundled agent skill by name.";
            leaf name {
                type string { length "1..64"; }
                mandatory true;
                description "A skill name as show skills prints it. An unknown name is refused.";
                ze:help "Skill name.";
            }
            leaf full {
                type empty;
                description "Print the expanded document, with examples and patterns, where the skill
carries one.";
                ze:help "Return expanded content (with examples and patterns).";
            }
        }

        container agent {
            config false;
            description "How the operator's agent harnesses are set up to use Ze.";
            ze:help "Inspect how the operator's agent is set up to use Ze.";

            container skill {
                config false;
                ze:command "ze-skills:show-agent-skill";
                description "At a shell, reports for each harness the plugin knows whether it was
found and whether the ze stub skill and, for Claude Code and Codex, the session-start hook are
installed, and changes no file. Through the daemon,
answers the stub a remote agent places, since the daemon cannot see the caller's home.";
                ze:help "Show whether the ze skill is set up for each agent harness.";
                uses agent-name;
            }

            container context {
                config false;
                ze:command "ze-skills:show-agent-context";
                description "The lines a session-start hook puts in front of the agent: the Ze
version, whether the daemon answers, and where the guide is. Through the daemon, the version
and that the caller reached the daemon.";
                ze:help "Show what an agent session is told about this Ze.";
            }
        }
    }

    container create {
        config false;

        container agent {
            config false;
            description "Set the operator's agent harnesses up to use Ze.";
            ze:help "Set an agent harness up to use Ze.";

            container skill {
                config false;
                ze:command "ze-skills:create-agent-skill";
                description "At a shell, installs the ze stub skill for every harness found or
for the one named, and with no harness found the shared stub Codex, OpenCode and Pi read.
For Claude Code and Codex it also adds one session-start hook to the harness's settings file,
leaving every other byte of that file as it was. Through the daemon, writes nothing and answers the stub a remote agent places.";
                ze:help "Install the ze skill for the operator's agent harnesses.";
                uses agent-name;
            }
        }
    }

    container delete {
        config false;

        container agent {
            config false;
            description "Remove what create agent skill installed.";
            ze:help "Remove the Ze setup from an agent harness.";

            container skill {
                config false;
                ze:command "ze-skills:delete-agent-skill";
                description "At a shell, removes the ze stub skill Ze installed, for the harness
named or, with no agent or agent all, for every harness found, takes its session-start hook out of the
harness's settings file, and leaves every file and hook Ze did not write. Through the daemon, writes nothing and answers the file a remote agent removes.";
                ze:help "Remove the ze skill from the operator's agent harnesses.";
                leaf agent {
                    type enumeration {
                        enum claude { ze:help "Claude Code."; }
                        enum codex { ze:help "Codex."; }
                        enum opencode { ze:help "OpenCode."; }
                        enum pi { ze:help "Pi."; }
                        enum all { ze:help "Every harness whose configuration directory exists."; }
                    }
                    description "The one harness to remove Ze's setup from. Without it, or with
all, delete acts on every harness whose configuration directory exists.";
                    ze:help "Agent harness, or all.";
                }
            }
        }
    }

    grouping agent-name {
        leaf agent {
            type enumeration {
                enum claude { ze:help "Claude Code."; }
                enum codex { ze:help "Codex."; }
                enum opencode { ze:help "OpenCode."; }
                enum pi { ze:help "Pi."; }
            }
            description "The one harness to act on. Without it create acts on every harness whose
configuration directory exists, and show reports every harness Ze knows.";
            ze:help "Agent harness.";
        }
    }
}
