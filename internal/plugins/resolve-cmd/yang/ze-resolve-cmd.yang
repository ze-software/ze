module ze-resolve-cmd {
    namespace "urn:ze:resolve:cmd";
    prefix resolvecmd;
    import ze-extensions { prefix ze; }
    import ze-types { prefix zt; }
    description "Look up DNS, ASN, PeeringDB, and IRR data from the router, inspect the DNS cache, and clear the DNS resolver cache. Owned by the resolve component because every handler reads or resets the resolver (resolvers.DNS). Container-merges onto the resolve, show, and clear verb roots. See ai/rules/plugin-self-containment.md.";
    revision 2026-04-04 { description "Initial revision"; }
    revision 2026-08-29 { description "Declare the value each lookup takes: the hostname of the A, AAAA and TXT lookups, the address of the reverse lookup, and the AS number of the Cymru and PeeringDB lookups. The descriptions spelled them in prose and the model stated nothing."; }
    revision 2026-06-03 { description "Relocated clear dns cache out of the central clear schema, and show dns lookup/cache out of the central show schema, into the resolve component (plugin self-containment)."; }
    revision 2026-09-02 { description "Add show resolve rir and update resolve rir: which Regional Internet Registry holds an AS number, and the operator order that refreshes the delegation table."; }
    revision 2026-10-17 { description "Clear dns cache needs all, record or stats, so the bare form flushes nothing. Add clear peeringdb cache, clear irr cache and clear cymru cache, each taking all or one key, answered by every owner of a resolver client."; }

    container resolve {
        config false;
        description "Each lookup runs on the router, so the answer is what the router reaches
and not what your workstation reaches. Each family of lookups needs its own resolver to be
configured.";
        ze:help "DNS, ASN, PeeringDB, and IRR resolution tools.";

        container dns {
            config false;
            description "The answers come from the daemon's own resolver and are stored in its
cache. A name that resolves to nothing is not cached, so the next lookup asks again.";
            ze:help "DNS record lookups from the router.";

            container a {
                config false;
                ze:command "ze-resolve:dns-a";
                ze:rpc "ze-resolve-api:dns-a";
                description "The answer is the list of IPv4 addresses. A valid cache entry
answers without a query, and a fresh answer is cached for the TTL the server gave.";
                ze:help "Look up IPv4 addresses (A records) for a hostname.";
                leaf hostname {
                    type string { length "1..253"; }
                    mandatory true;
                    description "A DNS name of 1 to 253 characters, which the router's own resolver
queries. The first word after the command is the name, and a call with no name is refused
with a usage line.";
                    ze:help "Hostname to look up.";
                }
            }
            container aaaa {
                config false;
                ze:command "ze-resolve:dns-aaaa";
                ze:rpc "ze-resolve-api:dns-aaaa";
                description "The answer is the list of IPv6 addresses. A valid cache entry
answers without a query, and a fresh answer is cached for the TTL the server gave.";
                ze:help "Look up IPv6 addresses (AAAA records) for a hostname.";
                leaf hostname {
                    type string { length "1..253"; }
                    mandatory true;
                    description "A DNS name of 1 to 253 characters, which the router's own resolver
queries. The first word after the command is the name, and a call with no name is refused
with a usage line.";
                    ze:help "Hostname to look up.";
                }
            }
            container txt {
                config false;
                ze:command "ze-resolve:dns-txt";
                ze:rpc "ze-resolve-api:dns-txt";
                description "Returns all TXT strings.";
                ze:help "Look up TXT records for a hostname.";
                leaf hostname {
                    type string { length "1..253"; }
                    mandatory true;
                    description "A DNS name of 1 to 253 characters, which the router's own resolver
queries. The first word after the command is the name, and a call with no name is refused
with a usage line.";
                    ze:help "Hostname to look up.";
                }
            }
            container ptr {
                config false;
                ze:command "ze-resolve:dns-ptr";
                ze:rpc "ze-resolve-api:dns-ptr";
                description "The address is turned into its in-addr.arpa or ip6.arpa name before
the query. The cache holds the answer under that name, so show dns cache record takes it in
that form.";
                ze:help "Reverse-lookup an IP address to its hostname (PTR).";
                leaf ip-address {
                    type string { pattern '[0-9a-fA-F:.]+(%[a-zA-Z0-9_.-]+)?'; }
                    mandatory true;
                    description "An IPv4 or IPv6 address in its usual text form. The resolver turns it
into the reverse name itself, so pass the address and not the in-addr.arpa name.";
                    ze:help "IP address to reverse-look-up.";
                }
            }
        }

        container cymru {
            config false;
            description "The router must have a Cymru resolver configured, and the command fails
without one. An AS number Team Cymru does not name answers (unknown) instead of an error.";
            ze:help "AS number lookups via Team Cymru.";

            container asn-name {
                config false;
                ze:command "ze-resolve:cymru-asn-name";
                ze:rpc "ze-resolve-api:cymru-asn-name";
                description "Queries Team Cymru DNS to return the organization name for the ASN.";
                ze:help "Find out who owns an AS number.";
                leaf asn {
                    type zt:asn-notated;
                    mandatory true;
                    description "The AS number in plain decimal or in asdot notation, which Ze parses to
one 32-bit value before the query. A spelling that parses to no AS number is refused.";
                    ze:help "AS number.";
                }
            }
        }

        container peeringdb {
            config false;
            description "The router must have a PeeringDB client configured, and both commands
fail without one. Each one takes an AS number.";
            ze:help "PeeringDB lookups for peering information.";

            container max-prefix {
                config false;
                ze:command "ze-resolve:peeringdb-max-prefix";
                ze:rpc "ze-resolve-api:peeringdb-max-prefix";
                description "Returns IPv4 and IPv6 prefix limits. Apply via the config editor.";
                ze:help "Get max-prefix limits for an ASN from PeeringDB.";
                leaf asn {
                    type zt:asn-notated;
                    mandatory true;
                    description "The AS number in plain decimal or in asdot notation, which Ze parses to
one 32-bit value before the query. A spelling that parses to no AS number is refused.";
                    ze:help "AS number.";
                }
            }
            container as-set {
                config false;
                ze:command "ze-resolve:peeringdb-as-set";
                ze:rpc "ze-resolve-api:peeringdb-as-set";
                description "Feed the result into 'resolve irr expand' to get the full member list.";
                ze:help "Find the IRR AS-SET registered for an ASN in PeeringDB.";
                leaf asn {
                    type zt:asn-notated;
                    mandatory true;
                    description "The AS number in plain decimal or in asdot notation, which Ze parses to
one 32-bit value before the query. A spelling that parses to no AS number is refused.";
                    ze:help "AS number.";
                }
            }
        }

        container irr {
            config false;
            description "The router must have an IRR client configured, and both commands fail
without one. Each one takes an AS-SET name rather than an AS number.";
            ze:help "Internet Routing Registry (WHOIS) queries.";

            container expand {
                config false;
                ze:command "ze-resolve:irr-expand";
                ze:rpc "ze-resolve-api:irr-expand";
                description "Recursively resolves nested AS-SET objects via WHOIS into a flat list. Useful
for building prefix filters from IRR data.";
                ze:help "Expand an AS-SET into its member AS numbers.";
            }
            container prefix {
                config false;
                ze:command "ze-resolve:irr-prefix";
                ze:rpc "ze-resolve-api:irr-prefix";
                description "Expands the AS-SET, then returns every route/route6 object for each member
ASN. Use this to build or verify prefix filters.";
                ze:help "Get all prefixes announced by an AS-SET's members.";
            }
        }
    }

    container show {
        config false;
        ze:help "Read-only commands to inspect system, protocol, and network state.";

        container dns {
            config false;
            description "show dns lookup asks the network and stores what it gets, so it fills
the cache. The cache commands under it only read.";
            ze:help "DNS lookups and cache inspection.";

            container lookup {
                config false;
                ze:command "ze-resolve:show-dns-lookup";
                description "Resolves <hostname> using the daemon's DNS resolver (falls back to the system
resolver if no DNS component is configured). Default type is A. Returns
records, TTL, and query time. Supports A, AAAA, MX, NS, TXT, CNAME, and PTR.";
                ze:help "Look up a DNS name from the router.";
                leaf hostname {
                    type string;
                    mandatory true;
                    description "A DNS name of at most 253 characters. The first word that is not the
type keyword is taken as the name, and a call with no name is refused.";
                    ze:help "Hostname to resolve.";
                }
                leaf type {
                    type enumeration {
                        enum A { ze:help "Ask for the IPv4 addresses of the name."; }
                        enum AAAA { ze:help "Ask for the IPv6 addresses of the name."; }
                        enum MX { ze:help "Ask for the mail exchanger hosts of the name."; }
                        enum NS { ze:help "Ask for the name servers of the name."; }
                        enum TXT { ze:help "Ask for the text strings published under the name."; }
                        enum CNAME { ze:help "Ask for the canonical name the name is an alias of."; }
                        enum PTR { ze:help "Ask for the host name a reverse name points to."; }
                    }
                    description "The record type to query, written after the type keyword. The default
is A. Ze upper-cases the value, and a type outside this list is refused with the list of
accepted ones.";
                    ze:help "DNS record type.";
                }
            }

            container cache {
                config false;
                description "Each operation is modeled as its own command so completion, help, and
generated references show distinct read-only actions.";
                ze:help "Inspect the DNS cache.";

                container stats {
                    config false;
                    ze:command "ze-resolve:show-dns-cache-stats";
                    description "It reads the counters and does not change the
cache contents.";
                    ze:help "Show the DNS cache hit, miss, eviction, expiry, and hit-rate counters.";
                }

                container list {
                    config false;
                    ze:command "ze-resolve:show-dns-cache-list";
                    description "An entry whose TTL has run out is left out rather than reported
as expired. The count beside the list is the number of entries reported.";
                    ze:help "List all non-expired DNS cache entries, sorted by shortest TTL first.";
                }

                container record {
                    config false;
                    ze:command "ze-resolve:show-dns-cache-record";
                    description "The name must match the cache key exactly, and a reverse lookup
is held under its in-addr.arpa or ip6.arpa name. A name that is not cached answers an empty
list and a count of zero.";
                    ze:help "Show DNS cache entries for one record name.";
                    leaf name {
                        type string;
                        mandatory true;
                        description "The cache key, compared as an exact string. Each entry reported
under it carries the name, the type, the records and the seconds of TTL left.";
                        ze:help "Record name to inspect.";
                    }
                }
            }
        }

        container resolve {
            config false;
            description "The data is held on the router, so no command here reaches the network.
update resolve is what refreshes it.";
            ze:help "Resolution data held on the router.";

            container rir {
                config false;
                ze:command "ze-resolve:show-rir";
                description "Reads the RIR delegation table that ships with the binary, or the newer
copy an earlier 'update resolve rir' stored. Reaches no network. Reports the
registry, its whois server, and the delegated range that holds the AS number.
An AS number in no delegated range and a table that cannot be read are two
different answers.";
                ze:help "Show which Regional Internet Registry holds an AS number.";
                leaf asn {
                    type zt:asn-notated;
                    mandatory true;
                    description "The AS number in plain decimal or in asdot notation, which Ze parses to
one 32-bit value before it searches the delegation table.";
                    ze:help "AS number to look up.";
                }
            }
        }
    }

    container update {
        config false;

        container resolve {
            config false;
            description "The refresh fetches the delegation file of each of the five Regional
Internet Registries. It stores nothing when any fetch or parse fails, so the previous table
stays in place.";
            ze:help "Refresh the resolution data held on the router.";

            container rir {
                config false;
                ze:command "ze-resolve:update-rir";
                description "Fetches the delegation file of each of the five Regional Internet
Registries, parses them, and stores one table under the meta/rir/delegation key.
All-or-nothing: a run in which any fetch or parse fails stores nothing and
leaves the previous copy in place.";
                ze:help "Refresh the RIR delegation table from the five registry delegation files.";
            }
        }
    }

    container clear {
        config false;

        container dns {
            config false;
            description "Every form needs a DNS resolver, and each one fails with DNS cache not
available without it. Nothing here reaches the network.";
            ze:help "DNS cache clearing operations.";

            container cache {
                config false;
                description "Clear dns cache alone is refused: say all to flush every entry, record
to evict one name, or stats to zero the counters. Everything is never the default.";
                ze:help "DNS cache clearing operations: all, record, or stats.";

                container all {
                    config false;
                    ze:command "ze-resolve:clear-dns-cache";
                    ze:rpc "ze-cli-clear-api:dns-cache";
                    description "The entries and the four counters go together. Use clear dns cache
stats to zero the counters and keep the entries, or clear dns cache record to evict one
name.";
                    ze:help "Flush all DNS cache entries and reset all DNS cache counters.";
                }

                container record {
                    config false;
                    ze:command "ze-resolve:clear-dns-cache-record";
                    description "Add type <record-type> after the name to evict one type, and
give no other tail. An unknown type is reported inside the answer rather than as an error.";
                    ze:help "Evict DNS cache entries for one record name, or one name and type when a type is provided.";
                    leaf name {
                        type string;
                        mandatory true;
                        description "The cache key, compared as an exact string. Alone, it evicts every
type cached under the name and the answer counts the entries removed.";
                        ze:help "Record name to evict.";
                    }
                    leaf type {
                        type enumeration {
                            enum A { ze:help "Evict the cached IPv4 addresses of the name."; }
                            enum AAAA { ze:help "Evict the cached IPv6 addresses of the name."; }
                            enum MX { ze:help "Evict the cached mail exchanger hosts of the name."; }
                            enum NS { ze:help "Evict the cached name servers of the name."; }
                            enum TXT { ze:help "Evict the cached text strings of the name."; }
                            enum CNAME { ze:help "Evict the cached canonical name of the name."; }
                            enum PTR { ze:help "Evict the cached reverse mapping of the name."; }
                        }
                        description "Written after the type keyword, it evicts that one type and leaves
the other types of the name in place. The answer reports found true or false.";
                        ze:help "Optional DNS record type to evict for the named record.";
                    }
                }

                container stats {
                    config false;
                    ze:command "ze-resolve:clear-dns-cache-stats";
                    description "The cached entries stay, so the next lookup is still served
from the cache. Only the hit, miss, eviction and expiry counters go to zero.";
                    ze:help "Reset DNS cache hit, miss, eviction, and expiry counters without removing cached entries.";
                }
            }
        }

        container peeringdb {
            config false;
            description "Each owner of a PeeringDB client clears the client it uses now: the
hub clears the one resolve peeringdb uses, and every plugin that declared the PeeringDB
cache, such as bgp-filter-irr and firewall-irr, clears its own, whether it runs inside the
daemon or as its own process. A client an owner replaced on a reload is not its own any
more and is not cleared or counted. The client bgp peer prefix update builds lives for one
command, so no clear reaches it. Nothing here reaches the network.";
            ze:help "PeeringDB client cache clearing operations.";

            container cache {
                config false;
                description "The cache holds the prefix counts and the AS-SET names of each AS
number for one hour. Name what to clear: all, or asn followed by an AS number. The bare
form clears nothing.";
                ze:help "Clear the PeeringDB cache: give all, or asn <number>.";

                container all {
                    config false;
                    ze:command "ze-resolve:clear-peeringdb-cache-all";
                    description "The answer gives removed, the entries removed in total, and
owners, one row per owner with the entries it removed. The next lookup of each AS number
queries PeeringDB again. An owner that does not answer makes the command an error naming
it.";
                    ze:help "Remove every cached PeeringDB answer.";
                }

                container asn {
                    config false;
                    ze:command "ze-resolve:clear-peeringdb-cache-asn";
                    description "Removes the prefix counts and the AS-SET names of one AS
number at every owner and keeps the other entries. The answer reports found true when any
owner held one, removed, and the owners rows.";
                    ze:help "Remove the cached PeeringDB answers of one AS number.";
                    leaf as-number {
                        type zt:asn-notated;
                        mandatory true;
                        description "The AS number in plain decimal or in asdot notation, which Ze
parses to one 32-bit value. A spelling that parses to no AS number is refused.";
                        ze:help "AS number to clear.";
                    }
                }
            }
        }

        container irr {
            config false;
            description "Each owner of an IRR client clears the client it uses now: the hub
clears the one resolve irr uses, and every plugin that declared the IRR cache, such as
bgp-filter-irr and firewall-irr, clears its own, whether it runs inside the daemon or as its
own process. A client an owner replaced on a reload is not cleared or counted. The stored
prefix lists those filters apply are not a cache and stay. Nothing here reaches the
network.";
            ze:help "IRR client cache clearing operations.";

            container cache {
                config false;
                description "The cache holds the members and the prefix list of each AS-SET for
one hour. Name what to clear: all, or as-set followed by a name. The bare form clears
nothing.";
                ze:help "Clear the IRR cache: give all, or as-set <name>.";

                container all {
                    config false;
                    ze:command "ze-resolve:clear-irr-cache-all";
                    description "The answer gives removed, the entries removed in total, and
owners, one row per owner with the entries it removed. The next lookup of each AS-SET
queries the whois server again. An owner that does not answer makes the command an error
naming it.";
                    ze:help "Remove every cached IRR answer.";
                }

                container as-set {
                    config false;
                    ze:command "ze-resolve:clear-irr-cache-as-set";
                    description "Removes the members and the prefix list of one AS-SET and keeps
the other entries, at every owner. The answer reports found true when any owner held one,
removed, and the owners rows.";
                    ze:help "Remove the cached IRR answers of one AS-SET.";
                    leaf name {
                        type string { length "1..255"; }
                        mandatory true;
                        description "The AS-SET name, compared as an exact string: give it as it was
looked up, for example AS-EXAMPLE. A name with a control character is refused.";
                        ze:help "AS-SET name to clear.";
                    }
                }
            }
        }

        container cymru {
            config false;
            description "The hub's Team Cymru resolver is cleared, and so is the one of every
plugin that declared the Cymru cache. Nothing here reaches the network.";
            ze:help "Team Cymru cache clearing operations.";

            container cache {
                config false;
                description "The cache holds the origin AS of each address and the name of each
AS for one hour. Name what to clear: all, or address followed by an IP address. The bare
form clears nothing.";
                ze:help "Clear the Cymru cache: give all, or address <ip>.";

                container all {
                    config false;
                    ze:command "ze-resolve:clear-cymru-cache-all";
                    description "Removes the address origins and the AS names. The answer gives
removed, the entries removed in total, and owners, one row per owner. The next lookup asks
DNS again.";
                    ze:help "Remove every cached Cymru answer.";
                }

                container address {
                    config false;
                    ze:command "ze-resolve:clear-cymru-cache-address";
                    description "Removes the origin of one address. The name of the AS it pointed
at stays cached, because it belongs to the AS. The answer reports found true when any owner
held it, removed, and the owners rows.";
                    ze:help "Remove the cached Cymru origin of one IP address.";
                    leaf ip-address {
                        type zt:ip-address;
                        mandatory true;
                        description "An IPv4 or IPv6 address. Any spelling of the address finds the
entry, so 2001:DB8::1 and 2001:db8:0::1 are the same key.";
                        ze:help "IP address to clear.";
                    }
                }
            }
        }
    }
}
