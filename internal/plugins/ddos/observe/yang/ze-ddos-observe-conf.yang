module ze-ddos-observe-conf {
  namespace "urn:ze:ddos-observe-conf";
  prefix ddos-observe;

  import ze-ddos-detect-conf { prefix dd; }
  import ze-extensions { prefix ze; }

  description "DDoS incident observation configuration. Augments the shared `ddos`
               container (owned by ze-ddos-detect-conf) with the `observe` subtree.";
  revision 2026-07-02 { description "Nest under ddos/observe: augment /dd:ddos with container observe."; }

  augment "/dd:ddos" {
    container observe {
      description "The ring is bounded and in memory, so it holds recent incidents and not a
                   history, and a restart empties it.";
      ze:help "Keep a ring of recent incidents for an operator to read back.";

      leaf incident-ring-size {
        type uint32 { range "1..100000"; }
        default 1000;
        description "The ring holds this many incidents. A new incident past the bound deletes the oldest
                     closed one. When every incident in the ring is still open, the oldest open one is
                     deleted instead. 1000 is the default, and the range is 1 to 100000.";
        ze:help "Maximum number of incidents to retain in memory.";
      }
      leaf stale-incident-timeout {
        type uint32 { range "1..86400"; }
        default 3600;
        description "The value reaches the incident store as its stale timeout, and no worker of ddos
            observe applies that timeout. The store closes an incident on the AttackCleared event that
            matches it. An incident that gets no clear event stays open until incident-ring-size evicts
            it. The default is 3600 seconds and the range is 1 to 86400. A value other than the default
            changes no behavior.";
        ze:help "Seconds before an open incident without a clear event is auto-finalized.";
      }
    }
  }
}
