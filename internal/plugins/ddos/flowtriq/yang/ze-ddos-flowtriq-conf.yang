module ze-ddos-flowtriq-conf {
  namespace "urn:ze:ddos-flowtriq-conf";
  prefix ddos-flowtriq;

  import ze-ddos-detect-conf { prefix dd; }
  import ze-extensions { prefix ze; }

  description "Flowtriq cloud reporting configuration. Augments the shared `ddos`
               container (owned by ze-ddos-detect-conf) with the `flowtriq` subtree.";
  revision 2026-07-02 { description "Nest under ddos/flowtriq: augment /dd:ddos with container flowtriq."; }

  augment "/dd:ddos" {
    container flowtriq {
      description "It reports and mitigates nothing on its own. The traffic still needs a
                   responder under flowspec or local to be stopped.";
      ze:help "Feed detected attacks to the FlowTriq reporting service.";

      leaf enabled {
        type boolean;
        default false;
        description "false is the default, and the reporter then posts nothing. true makes api-key and
                     node-uuid required, and Ze refuses the config when either one is empty. The reporter
                     answers an attack with one HTTP POST, and it stops no traffic.";
        ze:help "Enable reporting DDoS incidents to the Flowtriq cloud API.";
      }
      leaf api-key {
        type string { length "1..512"; }
        ze:sensitive;
        description "Ze sends the value in the Authorization header of each request, as a Bearer token.
                     The length is 1 to 512 characters. The leaf is required when enabled is true, and Ze
                     refuses the config without it. The leaf is marked sensitive, so every display path
                     prints a placeholder in place of the token. A $9$-encoded value written by hand is
                     decoded on read. Ze does not encode it for you, so a token typed into the editor is
                     written to the config file as you typed it.";
        ze:help "Flowtriq API bearer token.";
      }
      leaf node-uuid {
        type string { length "1..128"; }
        description "Ze sends the value in the X-Node-UUID header of each request, which is how the
                     service tells this router from another. The length is 1 to 128 characters. The leaf
                     is required when enabled is true.";
        ze:help "Node UUID for Flowtriq agent identification.";
      }
      leaf api-base {
        type string;
        default "https://flowtriq.com/api/v1";
        description "Ze appends a path to this value, so a trailing slash gives a double slash in the
                     request. /agent/incidents opens and closes an incident, and /agent/heartbeat reports
                     the baseline. Each request has a timeout of 10 seconds. After 5 failures Ze stops
                     posting for 60 seconds, then tries again.";
        ze:help "Flowtriq API base URL.";
      }
    }
  }
}
