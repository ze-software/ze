module ze-ddos-local-cmd {
    namespace "urn:ze:ddos-local:cmd";
    prefix ddoslocalcmd;
    import ze-extensions { prefix ze; }
    // The command container-merges onto the shared show ddos namespace, which
    // ddos-observe owns. Removing the plugin removes this node and its handler.
    // See ai/rules/plugin-self-containment.md.
    description "The show ddos local command, owned by the ddos-local plugin.";
    revision 2026-07-02 { description "Initial: show ddos local on-host mitigation status."; }

    container show {
        config false;
        ze:help "Read-only commands to inspect system, protocol, and network state.";

        container ddos {
            config false;
            description "Detection and mitigation are separate. A detected attack is reported even
                         when no mitigation is armed. An attack listed here does not prove that
                         traffic is dropped.";
            ze:help "Distributed denial-of-service detection and mitigation subsystem.";

            container local {
                config false;
                ze:command "ze-ddos:show-local";
                description "The answer states whether an nft drop rule is installed
now, and the target vector it covers: prefix, protocol, or port.";
                ze:help "Show the on-host DDoS mitigation status.";
            }
        }
    }
}
