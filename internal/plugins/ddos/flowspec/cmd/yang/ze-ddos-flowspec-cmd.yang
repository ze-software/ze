module ze-ddos-flowspec-cmd {
    namespace "urn:ze:ddos-flowspec:cmd";
    prefix ddosflowspeccmd;
    import ze-extensions { prefix ze; }
    description "show ddos flowspec command. Owned by the ddos-flowspec plugin; container-merges onto the shared show ddos namespace (owned by ddos-observe). Removing the plugin removes this node and its handler. See ai/rules/plugin-self-containment.md.";
    revision 2026-07-02 { description "Initial: show ddos flowspec upstream mitigation status."; }

    container show {
        config false;
        ze:help "Read-only commands to inspect system, protocol, and network state.";

        container ddos {
            config false;
            description "Detection and mitigation are separate. A detected attack is reported even
                         when no mitigation is armed. An attack listed here does not prove that
                         traffic is dropped.";
            ze:help "Distributed denial-of-service detection and mitigation subsystem.";

            container flowspec {
                config false;
                ze:command "ze-ddos:show-flowspec";
                description "The status names whether a rule is announced now, the
target vector that rule covers, and whether the leak-probe is running.";
                ze:help "Show the upstream FlowSpec and RTBH DDoS mitigation status.";
            }
        }
    }
}
