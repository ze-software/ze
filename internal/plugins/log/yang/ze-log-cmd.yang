module ze-log-cmd {
    namespace "urn:ze:log:cmd";
    prefix logcmd;
    import ze-extensions { prefix ze; }
    description "Log inspection and runtime level control. Owned by core/slogutil because these handlers read and configure the generic logging subsystem. See ai/rules/plugin-self-containment.md.";
    revision 2026-08-29 { description "request log level takes both values or it fails: handleLogSet reads args[0] and args[1] and refuses a shorter tail. The model declared them optional."; }
    revision 2026-06-06 { description "Relocated from central cmd/log schema (plugin self-containment). Wire methods retain ze-bgp: prefix for compatibility."; }

    container show {
        config false;
        ze:help "Read-only commands to inspect system, protocol, and network state.";

        container log {
            config false;
            description "The entries are what the daemon buffered, so the view starts at the last restart.
                         The level shown is what is live now, which can differ from the configured one.";
            ze:help "View log entries and current levels.";

            container levels {
                config false;
                ze:command "ze-log:bgp-log-levels";
                ze:rpc "ze-bgp-cmd-log-api:log-show";
                description "Lists every registered logger with its current level. Use 'request log level'
to change a level at runtime without restarting.";
                ze:help "Show what log level each subsystem is using.";
            }

            container recent {
                config false;
                ze:command "ze-log:bgp-log-recent";
                ze:rpc "ze-bgp-cmd-log-api:log-recent";
                description "Filters (all optional): level <lvl>, component <name>, count <N>. Newest
entries first. Useful when you cannot access the log file directly.";
                ze:help "Show recent log entries from the in-memory ring.";
                leaf level {
                    type enumeration {
                        enum disabled { ze:help "Matches no entry, because a buffered entry always carries a real level."; }
                        enum debug { ze:help "Keep the entries written at the debug level."; }
                        enum info { ze:help "Keep the entries written at the info level."; }
                        enum warn { ze:help "Keep the entries written at the warn level."; }
                        enum err { ze:help "Keep the entries written at the error level."; }
                    }
                    description "Keeps the entries whose level equals this value, and no other level. Without it
every level is shown.";
                    ze:help "Filter by log level";
                }
                leaf component {
                    type string;
                    description "Keeps the entries whose component name equals this value exactly. Without it every
component is shown.";
                    ze:help "Filter by component name";
                }
                leaf count {
                    type uint32;
                    description "Stops the answer after this many entries, newest first. It MUST be 1 or more, and
without it every buffered entry is shown.";
                    ze:help "Maximum number of entries";
                }
            }
        }
    }

    container request {
        config false;

        container log {
            config false;
            description "These act on the running daemon. A level set here is lost on restart, and the
                         configuration decides what a fresh process starts with.";
            ze:help "Runtime log operations.";

            container level {
                config false;
                ze:command "ze-log:bgp-log-set";
                ze:rpc "ze-bgp-cmd-log-api:log-set";
                description "Takes effect immediately. Set to debug when troubleshooting, then back to info
when you are done.";
                ze:help "Change a subsystem's log level without restarting.";
                leaf logger {
                    type string;
                    mandatory true;
                    description "The name of a registered logger, as 'show log levels' lists it. A name no logger
registered is refused.";
                    ze:help "Logger/subsystem name";
                }
                leaf target {
                    type enumeration {
                        enum disabled { ze:help "Write no entry until a later change sets a level again."; }
                        enum debug { ze:help "Write every entry, debug included."; }
                        enum info { ze:help "Write the info, warn and error entries and drop debug."; }
                        enum warn { ze:help "Write the warn and error entries and drop info and debug."; }
                        enum err { ze:help "Write the error entries alone."; }
                    }
                    mandatory true;
                    description "The level the logger writes at from now on. The value is matched without regard to
case, and 'error' and 'warning' are accepted as spellings of err and warn.";
                    ze:help "Target log level";
                }
            }
        }
    }
}
