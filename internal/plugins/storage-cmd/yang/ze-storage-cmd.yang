module ze-storage-cmd {
    namespace "urn:ze:storage:cmd";
    prefix storagecmd;
    import ze-extensions    { prefix ze; }
    import ze-cli-show-cmd  { prefix clishowcmd; }
    description "Storage show commands: SMART disk health monitoring.
         Relocated from the central show schema for plugin self-containment.";
    revision 2026-06-03 { description "Initial revision: relocated from ze-cli-show-cmd."; }

    augment "/clishowcmd:show" {
        container storage {
            config false;
            description "This reads the physical device through SMART. It is unrelated to show data, which
                         reads the blob store Ze keeps on top of it.";
            ze:help "Storage device health and diagnostics.";
            container smart {
                config false;
                ze:command "ze-storage:show-smart";
                description "Returns health status, temperature, power-on hours, and self-test schedule for
each block device. Replace drives that report failing health before they cause
data loss.";
                ze:help "Show disk health via SMART data.";
            }
        }
    }
}
