module ze-host-cmd {
    namespace "urn:ze:host:cmd";
    prefix hostcmd;
    import ze-extensions { prefix ze; }
    description "show host / show system kernel-log command tree. Owned by the host component because these handlers read hardware inventory (host.DetectSection) and kernel log (/dev/kmsg). See ai/rules/plugin-self-containment.md.";
    revision 2026-08-08 { description "Declared the bare 'show host' path as an alias of 'show host all'. Without it no wire method served the bare path, so the command worked with the daemon down (offline fallback) and answered 'unknown command' with it up."; }
    revision 2026-06-06 { description "Relocated show host and show system kernel-log out of the central show schema (plugin self-containment)."; }

    container show {
        config false;
        ze:help "Read-only commands to inspect system, protocol, and network state.";

        container host {
            config false;
            ze:command "ze-host:show-all";
            description "Sections: cpu, nic, dmi, memory, thermal, storage, kernel, platform. Use a
subcommand for one section, or 'show host all' for everything. The bare 'show
host' is an alias of 'show host all'.";
            ze:help "Hardware inventory for this box.";

            container cpu {
                config false;
                ze:command "ze-host:show-cpu";
                description "Returns vendor, model, core/thread topology, hybrid layout, scaling driver,
current/min/max frequencies, and throttle counts.";
                ze:help "Show what CPUs are in this box.";
            }

            container nic {
                config false;
                ze:command "ze-host:show-nic";
                description "Returns driver, PCI vendor/device IDs, link speed, queue counts, and firmware
version. Virtual interfaces are excluded. Use this to confirm NIC firmware
before an upgrade.";
                ze:help "Show physical NICs installed in this box.";
            }

            container dmi {
                config false;
                ze:command "ze-host:show-dmi";
                description "Returns system vendor, board name, BIOS version, and chassis type. Useful for
inventory or confirming which hardware model you are on.";
                ze:help "Show the box's identity from SMBIOS/DMI.";
            }

            container memory {
                config false;
                ze:command "ze-host:show-memory";
                description "Returns DIMM sizes and, when the edac driver is present, correctable and
uncorrectable error counters. Non-zero ECC counts mean you should plan a DIMM
replacement.";
                ze:help "Show installed memory and ECC health.";
            }

            container thermal {
                config false;
                ze:command "ze-host:show-thermal";
                description "Returns hwmon sensor readings and per-CPU throttle counters. Non-zero throttle
counts mean the box has been running hot enough to slow down.";
                ze:help "Show temperature sensors and thermal throttle events.";
            }

            container storage {
                config false;
                ze:command "ze-host:show-storage";
                description "Returns size, model, transport type (nvme, sata, mmc, virtio), rotational
flag, and NVMe firmware version where applicable.";
                ze:help "Show storage devices attached to this box.";
            }

            container kernel {
                config false;
                ze:command "ze-host:show-kernel";
                description "Returns kernel release, command line, CPU microcode revision, boot time, and
security-relevant CPU flags (spectre mitigations, etc.).";
                ze:help "Show the running kernel version and boot parameters.";
            }

            container platform {
                config false;
                ze:command "ze-host:show-platform";
                description "Reports read-only root, privilege level, systemd presence, gokrazy update
socket, reboot-allowed flag, persistent-storage writability, and fd limits.
Helps you understand what operations are possible on this particular
deployment.";
                ze:help "Show platform capabilities and constraints.";
            }

            container all {
                config false;
                ze:command "ze-host:show-all";
                description "Returns every section (cpu, nic, dmi, memory, thermal, storage, kernel,
platform) as a single JSON response. Ideal for support bundles or automated
inventory collection.";
                ze:help "Show the full hardware inventory in one shot.";
            }
        }

        container system {
            config false;

            container kernel-log {
                config false;
                ze:command "ze-host:show-system-kernel-log";
                description "Reads from /dev/kmsg. Filter by syslog level (emerg through debug) and limit
with count. Without count, you get the newest 50 messages. Linux only. Useful
for spotting NIC errors or OOM events.";
                ze:help "Show kernel log messages (dmesg-style).";
                leaf level {
                    type enumeration {
                        enum emerg { ze:help "Show only level 0, the system is unusable."; }
                        enum alert { ze:help "Show levels 0 to 1, action is needed at once."; }
                        enum crit { ze:help "Show levels 0 to 2, critical conditions."; }
                        enum err { ze:help "Show levels 0 to 3, error conditions."; }
                        enum warning { ze:help "Show levels 0 to 4, warning conditions."; }
                        enum notice { ze:help "Show levels 0 to 5, normal but significant events."; }
                        enum info { ze:help "Show levels 0 to 6, informational messages."; }
                        enum debug { ze:help "Show every level, 0 to 7, which is the default."; }
                    }
                    description "The word is the highest syslog level to show, and every more severe level
is included with it. A digit from 0 to 7 is accepted in its place. Absent, or not a
known level, nothing is filtered.";
                    ze:help "Filter by syslog level.";
                }
                leaf count {
                    type uint32;
                    description "The value is from 1 to 10000 and the default is 50. Ze reads the whole ring
buffer, applies the level filter, then keeps the newest count messages. A value outside
the range is ignored and the default applies.";
                    ze:help "Maximum number of messages.";
                }
            }
        }
    }
}
