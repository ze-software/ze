module ze-host-set-cmd {
    namespace "urn:ze:host:set:cmd";
    prefix hostsetcmd;
    import ze-extensions { prefix ze; }
    description "set system file-descriptors command. Owned by the host component because it adjusts process resource limits (setrlimit). See ai/rules/plugin-self-containment.md.";
    revision 2026-06-06 { description "Relocated set system file-descriptors out of the central set schema (plugin self-containment)."; }

    container set {
        config false;
        ze:help "Modify running configuration parameters.";

        container system {
            config false;
            description "These change the running host and are not written to the configuration, so a
                         reboot returns the machine to what its config describes.";
            ze:help "System-level runtime tunables.";

            container file-descriptors {
                config false;
                ze:command "ze-host:set-system-file-descriptors";
                description "Pass a number or 'max' to go to the hard limit. Takes effect immediately.
Check current limits with 'show system file-descriptors'.";
                ze:help "Raise the file descriptor limit for the daemon process.";
                leaf limit {
                    type union {
                        type uint64;
                        type enumeration {
                            enum max { ze:help "Raise the soft limit to the hard limit of the process."; }
                        }
                    }
                    description "The value is the new soft limit on open descriptors, a count from 1 up to
the hard limit, or the word max. Ze sets it with setrlimit and reports the previous,
the current and the hard limit. Zero, or a count above the hard limit, is refused.";
                    ze:help "New limit or max for hard limit.";
                }
            }
        }
    }
}
