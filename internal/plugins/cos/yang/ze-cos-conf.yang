module ze-cos-conf {
    namespace "urn:ze:cos:conf";
    prefix cos;

    import ze-types { prefix zt; }
    import ze-extensions { prefix ze; }

    description
        "Class-of-service profile definitions and interface bindings.
         Profiles define named 802.1p PCP-to-priority mappings that can
         be referenced from interface configuration instead of inline
         ingress-qos-map / egress-qos-map lists.";

    revision 2026-06-12 {
        description "Initial revision";
    }

    container request {
        config false;
        description "Operational actions that change the running subscriber policy.";
        ze:help "Request an operation on running state.";

        container class-of-service {
            description "These actions apply a named profile to a subscriber's access VLAN.";
            ze:help "Apply subscriber class-of-service policy.";

            container session {
                ze:command "ze-cos:session";
                description "The RADIUS owner prepares a change, applies its maps, then commits
it after every owner succeeds. Rollback restores the maps captured before prepare.";
                ze:help "Change one subscriber's VLAN marking maps.";

                leaf transaction {
                    type string { length "1..8192"; }
                    mandatory true;
                    description "One JSON object carries the operation and its session selection
or opaque token. This internal transaction is carried through authenticated command dispatch.";
                    ze:help "JSON transaction operation, selection or token.";
                }
            }
        }
    }

    container class-of-service {
        description "A profile maps the 3-bit PCP field of an 802.1Q header to an internal
priority, in the ingress direction and in the egress direction. An interface leaf and a
unit leaf name the profile they use.";
        ze:help "Named class-of-service profiles.";

        list ieee-802.1p {
            key "name";
            description "The profile defines the mapping between the 3-bit PCP field in the
802.1Q header and the internal priorities. It covers the ingress direction and the
egress direction.";
            ze:help "An 802.1p QoS profile.";

            leaf name {
                type zt:node-name;
                description "The name is the list key. The class-of-service leaf of an
interface, and of a unit, names one profile.";
                ze:help "Name of this profile, in lowercase letters, digits and hyphens.";
            }

            container ingress {
                description "Ze reads this mapping when it takes the internal priority of a
frame it receives.";
                ze:help "PCP-to-priority mapping of a received tagged frame.";

                list pcp {
                    key "value";
                    description "The list key is the PCP value, so the list holds at most one
entry for each of the eight values.";
                    ze:help "Map one received PCP value to an internal priority.";

                    leaf value {
                        type uint8 {
                            range "0..7";
                        }
                        description "IEEE 802.1Q defines the Priority Code Point field, which
is 3 bits wide and holds a value from 0 to 7.";
                        ze:help "PCP value in the 802.1Q header of the received frame.";
                    }

                    leaf priority {
                        type uint8 {
                            range "0..7";
                        }
                        mandatory true;
                        description "The value runs from 0 to 7.";
                        ze:help "Internal priority Ze gives to a matching frame.";
                    }
                }
            }

            container egress {
                description "Ze reads this mapping when it stamps the PCP field of a frame it
transmits.";
                ze:help "Priority-to-PCP mapping of a transmitted tagged frame.";

                list priority {
                    key "value";
                    description "The list key is the internal priority, so the list holds at
most one entry for each of the eight priorities.";
                    ze:help "Map one internal priority to a transmitted PCP value.";

                    leaf value {
                        type uint8 {
                            range "0..7";
                        }
                        description "The value runs from 0 to 7.";
                        ze:help "Internal priority of the outgoing packet.";
                    }

                    leaf pcp {
                        type uint8 {
                            range "0..7";
                        }
                        mandatory true;
                        description "IEEE 802.1Q defines the Priority Code Point field, which
is 3 bits wide and holds a value from 0 to 7.";
                        ze:help "PCP value Ze stamps in the 802.1Q header.";
                    }
                }
            }
        }
    }

    grouping cos-unit-leaves {
        description "Per-unit class-of-service profile reference,
                     merged into interface units via
                     container-merge.";

        leaf class-of-service {
            type string;
            description "The value is the name of a profile. The value 'none' stops the unit
from inheriting the profile of the parent interface.";
            ze:help "Class-of-service profile of this unit.";
        }

    }

    grouping cos-interface-leaves {
        description "Interface-level class-of-service leaf merged into L2
                     interface types via container-merge.";

        leaf class-of-service {
            type string;
            description "The value 'none' disables inheritance. When this leaf is set on the
interface, every VLAN unit inherits the profile. A unit that sets its own profile keeps
that one.";
            ze:help "Name of a class-of-service ieee-802.1p profile, or 'none'.";
        }
    }

    container interface {
        description "This container merges profile references into ze-iface-conf. Removing
the cos plugin removes these references; inline QoS maps remain owned by the interface component.";
        ze:help "Interface-level class-of-service profile bindings.";

        list ethernet {
            key "name";
            // The canonical node is owned by ze-iface-conf.yang. This module only
            // attaches the class-of-service leaves to it, and states the same fact
            // in wording the prose ratchet accepts.
            description "The cos plugin adds the class-of-service leaf to an ethernet interface. The leaf
names an ieee-802.1p profile, and every unit of the interface inherits it. A unit that sets its
own class-of-service keeps that one, and the value 'none' opts the unit out. Remove the cos
plugin and the leaf disappears from the interface.";
            ze:help "Physical or virtual Ethernet interface.";

            leaf name {
                type string;
                description "The cos plugin repeats the list key here, because its class-of-service
leaf merges onto the ethernet interface this name selects. The cos plugin adds no interface and
renames none: ze-iface-conf owns the interface itself.";
                ze:help "OS interface name, such as eth0 or ens3. It must match a kernel interface that exists.";
            }
            uses cos-interface-leaves;

            list unit {
                key "name";
                description "The cos plugin adds a profile reference to the unit. Its value
overrides the interface reference, and 'none' stops inheritance. Inline maps belong to
ze-iface-conf and remain available without this plugin. A profile and an inline map cannot
be used together, and both need vlan-id.";
                ze:help "Logical interface unit.";

                leaf name {
                    type zt:node-name;
                    description "The cos plugin repeats the list key here so its profile
reference reaches the named unit. The unit, its VLAN tag, addresses and inline QoS maps
belong to ze-iface-conf.";
                    ze:help "Unit name, in lowercase alphanumeric characters and hyphens.";
                }
                uses cos-unit-leaves;
            }
        }

        list dummy {
            key "name";
            // The canonical node is owned by ze-iface-conf.yang. This module only
            // attaches the class-of-service leaves to it, and states the same fact
            // in wording the prose ratchet accepts.
            description "The cos plugin adds the class-of-service leaf to a dummy interface. The leaf
names an ieee-802.1p profile, and every unit of the interface inherits it. A unit that sets its
own class-of-service keeps that one, and the value 'none' opts the unit out. Remove the cos
plugin and the leaf disappears from the interface.";
            ze:help "Dummy interface, which behaves like a loopback.";

            leaf name {
                type string;
                description "The cos plugin repeats the list key here, because its class-of-service
leaf merges onto the dummy interface this name selects. The cos plugin adds no interface and
renames none: ze-iface-conf owns the interface itself.";
                ze:help "Dummy interface name, such as dummy0. Ze creates the interface at apply time.";
            }
            uses cos-interface-leaves;

            list unit {
                key "name";
                description "The cos plugin adds a profile reference to the unit. Its value
overrides the interface reference, and 'none' stops inheritance. Inline maps belong to
ze-iface-conf and remain available without this plugin. A profile and an inline map cannot
be used together, and both need vlan-id.";
                ze:help "Logical interface unit.";

                leaf name {
                    type zt:node-name;
                    description "The cos plugin repeats the list key here so its profile
reference reaches the named unit. The unit, its VLAN tag, addresses and inline QoS maps
belong to ze-iface-conf.";
                    ze:help "Unit name, in lowercase alphanumeric characters and hyphens.";
                }
                uses cos-unit-leaves;
            }
        }

        list veth {
            key "name";
            // The canonical node is owned by ze-iface-conf.yang. This module only
            // attaches the class-of-service leaves to it, and states the same fact
            // in wording the prose ratchet accepts.
            description "The cos plugin adds the class-of-service leaf to a veth interface. The leaf
names an ieee-802.1p profile, and every unit of the interface inherits it. A unit that sets its
own class-of-service keeps that one, and the value 'none' opts the unit out. Remove the cos
plugin and the leaf disappears from the interface.";
            ze:help "Virtual ethernet pair interface";

            leaf name {
                type string;
                description "The cos plugin repeats the list key here, because its class-of-service
leaf merges onto the veth interface this name selects. The cos plugin adds no interface and
renames none: ze-iface-conf owns the interface itself.";
                ze:help "Veth interface name, such as veth0. Ze creates the pair at apply time.";
            }
            uses cos-interface-leaves;

            list unit {
                key "name";
                description "The cos plugin adds a profile reference to the unit. Its value
overrides the interface reference, and 'none' stops inheritance. Inline maps belong to
ze-iface-conf and remain available without this plugin. A profile and an inline map cannot
be used together, and both need vlan-id.";
                ze:help "Logical interface unit.";

                leaf name {
                    type zt:node-name;
                    description "The cos plugin repeats the list key here so its profile
reference reaches the named unit. The unit, its VLAN tag, addresses and inline QoS maps
belong to ze-iface-conf.";
                    ze:help "Unit name, in lowercase alphanumeric characters and hyphens.";
                }
                uses cos-unit-leaves;
            }
        }

        list bridge {
            key "name";
            // The canonical node is owned by ze-iface-conf.yang. This module only
            // attaches the class-of-service leaves to it, and states the same fact
            // in wording the prose ratchet accepts.
            description "The cos plugin adds the class-of-service leaf to a bridge interface. The leaf
names an ieee-802.1p profile, and every unit of the interface inherits it. A unit that sets its
own class-of-service keeps that one, and the value 'none' opts the unit out. Remove the cos
plugin and the leaf disappears from the interface.";
            ze:help "Linux bridge interface, which forwards Ethernet frames between member ports at L2.";

            leaf name {
                type string;
                description "The cos plugin repeats the list key here, because its class-of-service
leaf merges onto the bridge interface this name selects. The cos plugin adds no interface and
renames none: ze-iface-conf owns the interface itself.";
                ze:help "Bridge interface name, such as br0. Ze creates the bridge at apply time.";
            }
            uses cos-interface-leaves;

            list unit {
                key "name";
                description "The cos plugin adds a profile reference to the unit. Its value
overrides the interface reference, and 'none' stops inheritance. Inline maps belong to
ze-iface-conf and remain available without this plugin. A profile and an inline map cannot
be used together, and both need vlan-id.";
                ze:help "Logical interface unit.";

                leaf name {
                    type zt:node-name;
                    description "The cos plugin repeats the list key here so its profile
reference reaches the named unit. The unit, its VLAN tag, addresses and inline QoS maps
belong to ze-iface-conf.";
                    ze:help "Unit name, in lowercase alphanumeric characters and hyphens.";
                }
                uses cos-unit-leaves;
            }
        }
    }
}
