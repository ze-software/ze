module ze-l2tp-pool-conf {
    namespace "urn:ze:l2tp:pool:conf";
    prefix l2tp-pool;
    import ze-types { prefix zt; }
    import ze-extensions { prefix ze; }

    description
        "Static IPv4 address pool for L2TP PPP sessions.
         Allocates addresses from configured ranges using a
         bitmap-backed pool. Releases on session-down.";

    container l2tp {
        container pool {
            container ipv4 {
                leaf gateway {
                    type zt:ipv4-address;
                    mandatory true;
                    description
                        "NAS-side IP for all PPP sessions (IPCP local address).
                         Must not overlap the pool range.";
                }
                leaf start {
                    type zt:ipv4-address;
                    description "First address in the pool range.";
                }
                leaf end {
                    type zt:ipv4-address;
                    description "Last address in the pool range (inclusive).";
                }
                leaf dns-primary {
                    type zt:ipv4-address;
                    description "Primary DNS server pushed to subscribers.";
                }
                leaf dns-secondary {
                    type zt:ipv4-address;
                    description "Secondary DNS server pushed to subscribers.";
                }
            }
            list named-pool {
                key "name";
                description
                    "Named IPv4 pools selected by RADIUS Framed-Pool attribute.";
                leaf name {
                    type string;
                    description "Pool name matching RADIUS Framed-Pool value.";
                }
                leaf gateway {
                    type zt:ipv4-address;
                    mandatory true;
                    description "NAS-side IP for sessions using this pool.";
                }
                leaf start {
                    type zt:ipv4-address;
                    mandatory true;
                    description "First address in the pool range.";
                }
                leaf end {
                    type zt:ipv4-address;
                    mandatory true;
                    description "Last address in the pool range (inclusive).";
                }
                leaf dns-primary {
                    type zt:ipv4-address;
                    description "Primary DNS server pushed to subscribers.";
                }
                leaf dns-secondary {
                    type zt:ipv4-address;
                    description "Secondary DNS server pushed to subscribers.";
                }
            }
        }
    }
}
