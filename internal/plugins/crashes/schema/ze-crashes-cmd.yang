module ze-crashes-cmd {
    namespace "urn:ze:crashes:cmd";
    prefix crashescmd;
    import ze-extensions { prefix ze; }
    description "show crashes command tree. Owned by the crashes plugin because the handler reads crash files through the crashlog package. See ai/rules/plugin-self-containment.md.";
    revision 2026-06-06 { description "Relocated show crashes out of the central show schema (plugin self-containment)."; }

    container show {
        config false;
        description "Read-only commands to inspect system, protocol, and network state";

        container crashes {
            config false;
            ze:command "ze-show:crashes";
            description "View saved crash reports from panics.
Without arguments, lists available crash files. Use 'latest' to see
the newest crash or 'name <filename>' to print one specific report.
Send the output to support when reporting a crash.";
            leaf name {
                type string;
                description "Crash report name (used with 'name <filename>')";
            }
        }
    }
}
