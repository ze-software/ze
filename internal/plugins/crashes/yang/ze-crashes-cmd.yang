module ze-crashes-cmd {
    namespace "urn:ze:crashes:cmd";
    prefix crashescmd;
    import ze-extensions { prefix ze; }
    // The handler reads crash files through the crashlog package.
    // See ai/rules/plugin-self-containment.md.
    description "The show crashes command tree, owned by the crashes plugin.";
    revision 2026-06-06 { description "Relocated show crashes out of the central show schema (plugin self-containment)."; }

    container show {
        config false;
        ze:help "Read-only commands to inspect system, protocol, and network state.";

        container crashes {
            config false;
            ze:command "ze-crashes:show-crashes";
            description "Without arguments, lists every stored report with its kind: 'panic' for a Go
panic this daemon caught, 'kernel' for a kernel fault recovered from the
reserved region on the following boot. The listing also carries a readiness
block, which reports configured and armed separately because the reservation
is a kernel boot argument and a commit alone does not arm it. Use 'latest' to
see the newest report or 'name <filename>' to print one. Send the output to
support when reporting a crash.";
            ze:help "View saved crash reports, and whether kernel capture is armed.";
            leaf name {
                type string;
                description "The file name of one stored report, as the listing prints it. Ze reads
that file from the crash directory and prints it. A name holding a slash or '..' is
refused.";
                ze:help "Crash report name (used with 'name <filename>').";
            }
        }
    }
}
