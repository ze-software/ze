module ze-rsvp-te-conf {
    namespace "urn:ze:rsvp-te:conf";
    prefix rsvpteconf;
    import ze-extensions { prefix ze; }
    description "RSVP-TE protocol configuration (RFC 3209)";
    revision 2026-05-28 { description "Initial revision"; }

    container rsvp-te {
        description "RSVP-TE traffic engineering configuration. Signaling is IPv4 only. Without a router-id the engine stays
            idle, and no tunnel and no bypass signals. RSVP-TE does not consume a traffic-engineering database
            or run CSPF, so paths are configured explicitly.";
        ze:help "RSVP-TE traffic engineering configuration";

        leaf router-id {
            type string;
            description "Router identifier, in IPv4 address format. A commit that gives an IPv6 address is rejected. The
                address is the PATH sender address, the address the transport socket binds, and the seed of the
                session key each tunnel and bypass derives. A change after startup is logged and refused, and the
                running router-id stays in use until the daemon restarts.";
            ze:help "Router identifier (IPv4 address format)";
        }

        leaf refresh-period {
            type uint16 {
                range "1..65535";
            }
            default 30;
            units seconds;
            description "PATH and RESV refresh interval, 1 to 65535 seconds, default 30. The same 65535-second ceiling caps
                the period a neighbor advertises in TIME_VALUES. A neighbor therefore cannot hold state alive for
                years. A
                reload reaches the running LSPs at the next refresh tick.";
            ze:help "PATH/RESV refresh interval (RFC 2205 soft-state)";
        }

        leaf refresh-multiplier {
            type uint8 {
                range "1..255";
            }
            default 3;
            description "Number of missed refreshes before state cleanup, 1 to 255, default 3. State expires when the last
                refresh is older than refresh-period multiplied by this number, which is 90 seconds at the
                defaults. Expiry releases the reserved bandwidth, the MPLS forwarding entry and the label, then
                sends an lsp-down event.";
            ze:help "Number of missed refreshes before state cleanup";
        }

        container reservation-policy {
            description "Local network-address authorization for RSVP reservations. Rules match the IPv4 sender in
                SENDER_TEMPLATE or FILTER_SPEC and the tunnel endpoint in SESSION. Authorization and bandwidth
                admission must both permit a reservation. This policy does not provide cryptographic user
                authentication or interpret POLICY_DATA objects.";
            ze:help "Local reservation authorization by sender and tunnel endpoint";

            leaf default-action {
                type enumeration {
                    enum permit { ze:help "Permit a reservation when no rule matches."; }
                    enum deny { ze:help "Deny a reservation when no rule matches."; }
                }
                default permit;
                description "Action when no rule matches. The default is permit, so configurations without a
                    reservation policy keep their existing authorization behavior.";
                ze:help "Action when no reservation rule matches";
            }

            list rule {
                key "index";
                description "Rules are evaluated by ascending numeric index. The first matching rule decides.
                    Both configured prefixes must match. An omitted prefix matches every address; a rule with
                    neither prefix matches every reservation.";
                ze:help "Reservation authorization rule";

                leaf index {
                    type uint16;
                    description "Evaluation order from 0 to 65535, lowest first. Use a decimal integer without
                        leading zeros. The index decides precedence, regardless of configuration file order.";
                    ze:help "Rule index, lowest first";
                }

                leaf sender-prefix {
                    type string {
                        length "7..18";
                    }
                    ze:validate "ipv4-prefix";
                    description "IPv4 prefix for the sender address. A /32 matches one host and /0 matches every
                        IPv4 sender. Host bits are masked before matching. Omit this leaf to match any sender.";
                    ze:help "Sender IPv4 prefix";
                }

                leaf endpoint-prefix {
                    type string {
                        length "7..18";
                    }
                    ze:validate "ipv4-prefix";
                    description "IPv4 prefix for the SESSION tunnel endpoint. A /32 matches one host and /0
                        matches every IPv4 endpoint. Host bits are masked before matching. Omit this leaf to
                        match any tunnel endpoint.";
                    ze:help "Tunnel endpoint IPv4 prefix";
                }

                leaf action {
                    type enumeration {
                        enum permit { ze:help "Permit a reservation that matches this rule."; }
                        enum deny { ze:help "Deny a reservation that matches this rule."; }
                    }
                    mandatory true;
                    description "Required authorization decision for a matching reservation. A permit still
                        requires bandwidth admission.";
                    ze:help "Authorization action for a matching reservation";
                }
            }
        }

        list interface {
            key "name";
            description "Per-interface RSVP-TE configuration. Bandwidth admission control accounts each reservation against
                one entry of this list. An interface that no entry names carries no limit, so every reservation
                that resolves onto it is admitted.";
            ze:help "Per-interface RSVP-TE configuration";

            leaf name {
                type string;
                description "Interface name, and the key of this list. With one entry configured, every reservation is
                    accounted against that entry. With more than one, the entry whose address prefix contains the
                    LSP neighbor owns the reservation. An LSP that matches no prefix is not accounted at all.";
                ze:help "Interface name";
            }

            leaf max-bandwidth {
                type string;
                description "Maximum link bandwidth. The value is reported by 'show rsvp-te interface' and it is not an
                    admission limit. Only max-reservable-bandwidth bounds what admission control accepts.";
                ze:help "Maximum link bandwidth (bps)";
            }

            leaf max-reservable-bandwidth {
                type string;
                description "Maximum reservable bandwidth. Admission control denies a reservation when the accounted total
                    plus the new request is more than this value. A shared-explicit session counts its largest LSP
                    once rather than the sum, so a make-before-break reroute is not double-counted. Left unset, the
                    limit is 0 and every tunnel that requests bandwidth on this interface is denied.";
                ze:help "Maximum reservable bandwidth (bps)";
            }

            leaf address {
                type string;
                description "Local link prefix (IPv4 CIDR, for example 10.0.0.4/30). When more than one interface is configured,
                    admission control maps an LSP to this interface. The map applies when the neighbor address falls
                    within the prefix.";
                ze:help "Local link prefix in IPv4 CIDR form, for example 10.0.0.4/30.";
            }
        }

        list tunnel {
            key "name";
            description "RSVP-TE LSP tunnel definition. Each entry signals a PATH from the local router-id toward
                destination. A commit that changes only the explicit route starts a make-before-break reroute (RFC
                3209 Section 6.1) and leaves the live tunnel in place.";
            ze:help "RSVP-TE LSP tunnel definition";

            leaf name {
                type string;
                description "Tunnel name, and the key of this list. Ze puts the name in the SESSION_ATTRIBUTE object, and it
                    adds that object only for a tunnel that also declares fast-reroute. No router on the path
                    reads the name of an unprotected tunnel.";
                ze:help "Tunnel name";
            }

            leaf destination {
                type string;
                description "Tunnel endpoint, an IPv4 address. The address is the SESSION tunnel endpoint the PATH carries.
                    A node whose own router-id equals this address acts as the egress and answers with a RESV. Every
                    other node on the path acts as a transit node.";
                ze:help "Tunnel endpoint (IPv4 address)";
            }

            leaf tunnel-id {
                type uint16;
                description "Tunnel identifier, the part of the SESSION that separates this LSP from another to the same
                    endpoint. Ze reserves 61440 to 65535 for the bypass LSPs it derives from a bypass name, and a
                    commit that puts a tunnel in that range is rejected.";
                ze:help "Tunnel identifier";
            }

            leaf bandwidth {
                type string;
                description "Requested bandwidth. The value fills the SENDER_TSPEC token rate, token bucket and peak rate.
                    Admission control charges it against the interface entry the LSP neighbor resolves onto, and it
                    denies the LSP when the charge is more than max-reservable-bandwidth.";
                ze:help "Requested bandwidth (bps)";
            }

            leaf setup-priority {
                type uint8 {
                    range "0..7";
                }
                default 7;
                description "Setup priority, where 0 is the highest and 7 is the default. Ze signals the value in the
                    SESSION_ATTRIBUTE and FAST_REROUTE objects, and it adds both objects only for a tunnel that
                    declares fast-reroute. Ze preempts no LSP of its own, so the priority acts on the routers
                    downstream.";
                ze:help "Setup priority (0 = highest)";
            }

            leaf hold-priority {
                type uint8 {
                    range "0..7";
                }
                default 7;
                description "Hold priority, where 0 is the highest and 7 is the default. It states how hard this LSP holds
                    its reservation against a setup of higher priority. Ze signals it beside setup-priority, and
                    only for a tunnel that declares fast-reroute.";
                ze:help "Hold priority (0 = highest)";
            }

            container fast-reroute {
                presence "request RFC 4090 local protection for this tunnel";
                description "Fast Reroute (RFC 4090) local protection for this LSP. The container has presence. Absent, the
                    head-end PATH carries no SESSION_ATTRIBUTE and no FAST_REROUTE object, and no transit PLR arms a
                    backup. Present, it also puts setup-priority, hold-priority and the tunnel name on the wire.";
                ze:help "Fast Reroute (RFC 4090) local protection for this LSP";

                leaf backup {
                    type enumeration {
                        enum facility { ze:help "Ask each PLR for one bypass LSP that protects many LSPs (RFC 4090 Section 3.2)."; }
                        enum one-to-one { ze:help "Ask for one detour per LSP (RFC 4090 Section 3.1), which Ze signals and never builds."; }
                    }
                    default facility;
                    description "Backup method. facility is the default and asks each PLR for one bypass LSP that protects
                        many LSPs (RFC 4090 Section 3.2). one-to-one asks for one detour per LSP (Section 3.1). As a
                        PLR, Ze arms only a facility bypass from its own bypass list. Ze signals a one-to-one request
                        and builds no detour for it.";
                    ze:help "Backup method: facility (one bypass protects many LSPs) or one-to-one (a detour per LSP)";
                }

                leaf node-protection {
                    type boolean;
                    default false;
                    description "Request NNHOP (node) protection rather than NHOP (link) protection. Ze sets the
                        node-protection flag in SESSION_ATTRIBUTE (RFC 4090 Section 4.3). As a PLR, Ze then arms only
                        a bypass whose merge point is the next-next hop of the explicit route. That bypass also has
                        to set its own node-protection leaf. With no such bypass, the LSP gets no protection.";
                    ze:help "Request NNHOP (node) protection rather than NHOP (link) protection";
                }

                leaf bandwidth-protection {
                    type boolean;
                    default false;
                    description "Request a backup that guarantees the reserved bandwidth. Ze sets the bandwidth-protection
                        flag in SESSION_ATTRIBUTE (RFC 4090 Section 4.3) and records it in the RESV route object. Ze's
                        own bypass selection does not compare the bypass bandwidth, so the flag is a request to the
                        PLR downstream.";
                    ze:help "Request a backup that guarantees the reserved bandwidth";
                }

                leaf hop-limit {
                    type uint8 {
                        range "0..255";
                    }
                    default 16;
                    description "Maximum number of hops the backup path can take, 0 to 255, default 16. The value goes into
                        the FAST_REROUTE object (RFC 4090 Section 4.1) for the PLR that computes the backup. A Ze
                        facility bypass is routed by its own explicit-route list, so this limit does not shorten
                        it.";
                    ze:help "Maximum number of hops the backup path can take";
                }
            }

            list explicit-route {
                key "index";
                ordered-by user;
                description "Explicit route hops. The list becomes the ERO object the PATH carries (RFC 3209 Section 4.3).
                    RSVP-TE does not run CSPF, so the operator supplies the hops. A tunnel with no hop here is signaled
                    with no ERO object. A commit that changes the list starts a make-before-break reroute.";
                ze:help "Explicit route hops";

                leaf index {
                    type uint16;
                    description "Hop index, and the key of this list. Ze sorts the hops by this number. The index decides
                        the order of the path rather than the order of the statements in the config file.";
                    ze:help "Hop index";
                }

                leaf address {
                    type string;
                    description "Hop address, given as an IPv4 prefix such as 10.0.0.4/30. A commit that gives a bare
                        address with no prefix length is rejected. The address and the prefix length both go into
                        the ERO IPv4 prefix subobject.";
                    ze:help "Hop address (IPv4 prefix)";
                }

                leaf type {
                    type enumeration {
                        enum strict { ze:help "The previous hop must reach this one directly, with no hop between them."; }
                        enum loose { ze:help "Set the L bit of the ERO subobject and permit other hops between them."; }
                    }
                    default strict;
                    description "Hop type. strict is the default and asks that the previous hop reaches this one directly.
                        loose sets the L bit of the ERO subobject and permits other hops between them. Ze reads any
                        value other than loose as strict.";
                    ze:help "Hop type (strict or loose)";
                }
            }
        }

        list bypass {
            key "name";
            description "Facility-backup bypass LSP (RFC 4090 Section 3.2): an LSP from this PLR to a merge point, explicitly
                routed to avoid the protected resource. A protected transit LSP is redirected onto this bypass on a
                local failure. The redirected LSP is one whose next hop (link protection) or next-next hop (node
                protection) is this bypass's merge point. RSVP-TE does not consume a traffic-engineering database
                or run CSPF to compute a backup path.";
            ze:help "Facility-backup bypass LSP from this PLR to a merge point (RFC 4090 Section 3.2).";

            leaf name {
                type string;
                description "Bypass name, and the key of this list. Ze hashes the name into its reserved tunnel-id range to
                    key the bypass LSP. Two names that hash to the same key are rejected at commit, and one of them
                    is renamed. The list holds 1024 bypasses at most.";
                ze:help "Bypass name";
            }

            leaf merge-point {
                type string;
                description "Merge point address (IPv4). The address is the protected LSPs' next hop (link protection) or
                    next-next hop (node protection), where this bypass rejoins them.";
                ze:help "Merge point address (IPv4) where this bypass rejoins the protected LSPs.";
            }

            leaf node-protection {
                type boolean;
                default false;
                description "This bypass merges at a next-next hop, so it gives node protection. A protected LSP that asked
                    for node protection is armed onto a bypass only when this leaf is true. Left false, the bypass
                    protects the link alone, and a node-protection request finds no bypass at this PLR.";
                ze:help "This bypass merges at a next-next hop, so it gives node protection";
            }

            list explicit-route {
                key "index";
                ordered-by user;
                description "Bypass path hops. The route has to avoid the link or the node this bypass protects, because a
                    backup that crosses the protected resource fails with it. RSVP-TE does not run CSPF, so the
                    operator supplies the hops. The hops are ordered by the numeric index key.";
                ze:help "Bypass path hops (must avoid the protected resource)";

                leaf index {
                    type uint16;
                    description "Hop index, and the key of this list. Ze sorts the bypass hops by this number. The index
                        decides the order of the path rather than the order of the statements in the config file.";
                    ze:help "Hop index";
                }

                leaf address {
                    type string;
                    description "Hop address, given as an IPv4 prefix such as 10.0.0.8/30. A commit that gives a bare
                        address with no prefix length is rejected. The address and the prefix length both go into
                        the ERO IPv4 prefix subobject of the bypass PATH.";
                    ze:help "Hop address (IPv4 prefix)";
                }

                leaf type {
                    type enumeration {
                        enum strict { ze:help "The previous hop must reach this one directly, with no hop between them."; }
                        enum loose { ze:help "Set the L bit of the ERO subobject and permit other hops between them."; }
                    }
                    default strict;
                    description "Hop type. strict is the default and asks that the previous hop reaches this one directly.
                        loose sets the L bit of the ERO subobject and permits other hops between them. Ze reads any
                        value other than loose as strict.";
                    ze:help "Hop type (strict or loose)";
                }
            }
        }
    }
}
