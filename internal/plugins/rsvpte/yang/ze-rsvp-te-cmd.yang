module ze-rsvp-te-cmd {
    namespace "urn:ze:rsvp-te:cmd";
    prefix rsvptecmd;
    import ze-extensions { prefix ze; }
    description "show rsvp-te ... command tree. Owned by the rsvp-te component so that removing it removes these command nodes together with the handlers. See ai/rules/plugin-self-containment.md.";
    revision 2026-06-03 { description "Relocated show rsvp-te ... out of the central show schema (plugin self-containment)."; }
    revision 2026-06-19 { description "Add show rsvp-te fast-reroute (RFC 4090 protection state)."; }

    container show {
        config false;
        ze:help "Read-only commands to inspect system, protocol, and network state.";

        container rsvp-te {
            config false;
            description "A reservation here is what RSVP-TE signalled, which is a control-plane promise.
                         It is not a measurement of the traffic actually crossing the LSP.";
            ze:help "RSVP-TE LSPs, tunnels, and bandwidth reservations.";

            container lsp {
                config false;
                ze:command "ze-rsvpte:show-rsvp-te-lsp";
                description "Returns state, role (ingress/transit/egress, or unspecified while the message or
configuration that created the LSP is still being handled), reserved bandwidth, and in/out labels for each LSP.";
                ze:help "Show RSVP-TE label-switched paths.";
            }

            container interface {
                config false;
                ze:command "ze-rsvpte:show-rsvp-te-interface";
                description "Returns reserved, available, and maximum bandwidth for each TE-enabled
interface.";
                ze:help "Show RSVP-TE bandwidth allocation per interface.";
            }

            container tunnel {
                config false;
                ze:command "ze-rsvpte:show-rsvp-te-tunnel";
                description "Returns tunnel name, endpoints, signaling state, and active LSP.";
                ze:help "Show configured RSVP-TE tunnels and their current state.";
            }

            container fast-reroute {
                config false;
                ze:command "ze-rsvpte:show-rsvp-te-fast-reroute";
                description "Returns each configured facility-backup bypass LSP and each protected LSP with
its armed bypass, mode, and whether local protection is available and in use.";
                ze:help "Show RSVP-TE Fast Reroute (RFC 4090) protection state.";
            }
        }
    }
}
