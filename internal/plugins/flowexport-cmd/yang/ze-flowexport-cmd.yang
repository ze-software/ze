module ze-flowexport-cmd {
    namespace "urn:ze:flowexport:cmd";
    prefix flowexportcmd;
    import ze-extensions { prefix ze; }
    // Removing the component removes the command node together with the handler.
    // See ai/rules/plugin-self-containment.md.
    description "The show flow command tree, owned by the flowexport component.";
    // They were flow-export and flow-recent, and the CLI hyphen namespace split
    // moved them.
    revision 2026-07-13 { description "Nest under show flow export and show flow recent."; }
    revision 2026-07-01 { description "Add show flow-recent (recent-flow ring query for DDoS characterization)."; }
    revision 2026-06-03 { description "Relocated show flow-export out of the central show schema (plugin self-containment)."; }

    container show {
        config false;
        ze:help "Read-only commands to inspect system, protocol, and network state.";

        container flow {
            config false;
            description "The ring is bounded and in memory, so it holds recent flows rather than a history.
                         Export status says whether the collector is being reached, which is separate from
                         whether flows are being seen.";
            ze:help "Flow observability: NetFlow/IPFIX export status and the recent-flow ring.";

            container export {
                config false;
                ze:command "ze-flowexport:show-flow-export";
                description "Without arguments, lists all configured collectors. With 'name <name>', shows
details for that collector including protocol stats and errors. Returns
not-configured when no exporter is active.";
                ze:help "Show flow export (NetFlow/IPFIX) collector status.";
                leaf name {
                    type string;
                    description "The value is the key of a configured collector. Ze returns that one
collector with its protocol counters and errors, and answers 'collector not found' for
any other value.";
                    ze:help "Collector name (used with 'name <name>').";
                }
            }

            container recent {
                config false;
                ze:command "ze-flowexport:show-flow-recent";
                description "Without arguments, returns every ring record (oldest to newest, up to the
configured recent-flow-ring capacity). With 'dst <prefix>', filters to flows
whose destination is inside that prefix. The ring is fed only while conntrack
export is enabled; the filter is by destination prefix (conntrack is
host-global and carries no ingress interface).";
                ze:help "Show recent conntrack flow records from the bounded recent-flow ring.";
                leaf dst {
                    type string;
                    description "The value is an IPv4 or IPv6 prefix in CIDR form, or a bare address,
which Ze reads as a /32 or a /128. Ze keeps only the ring records whose destination is
inside that prefix.";
                    ze:help "Destination prefix or address to filter by (used with 'dst <prefix>').";
                }
            }
        }
    }
}
