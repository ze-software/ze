module ze-bgp-conf {
    namespace "urn:ze:bgp:conf";
    prefix bgp;

    import ze-types { prefix zt; }
    import ze-extensions { prefix ze; }

    description "BGP configuration for ZeBGP";

    revision 2026-01-01 {
        description "Initial revision";
    }

    // Template block - peer templates
    container template {
        description "Peer templates";

        container bgp {
            description "BGP templates";
            list peer {
                key "pattern";
                description "Peer pattern template";

                leaf pattern {
                    type string;
                    description "Pattern to match peer addresses";
                }

                leaf inherit-name {
                    type string;
                    description "Named template identifier";
                }

                uses peer-fields;
            }
        }

        // Legacy syntax support
        list group {
            key "name";
            description "Legacy group template";
            leaf name { type string; }
            uses peer-fields;
        }

        list match {
            key "pattern";
            description "Legacy match template";
            leaf pattern { type string; }
            uses peer-fields;
        }
    }

    // BGP block - main BGP configuration
    container bgp {
        description "BGP configuration";

        leaf router-id {
            type zt:ipv4-address;
            mandatory true;
            description "BGP Router ID (required)";
        }

        leaf local-as {
            type zt:asn;
            mandatory true;
            description "Local Autonomous System Number (required)";
        }

        leaf listen {
            type string;
            description "Listen address and port";
        }

        list peer {
            key "address";
            description "BGP peer configuration";

            leaf address {
                type zt:ip-address;
                description "Peer IP address";
            }

            uses peer-fields;
        }
    }

    // Grouping for peer configuration fields
    grouping peer-fields {
        description "Common peer configuration fields";

        // Template inheritance
        leaf inherit {
            type string;
            description "Inherit from template";
        }

        // Basic peer identification
        leaf description {
            type string;
            description "Peer description";
        }

        leaf router-id {
            type zt:ipv4-address;
            description "Override router ID for this peer";
        }

        leaf local-address {
            type string;
            mandatory true;
            description "Local address for connection (use IP address or 'auto')";
        }

        leaf link-local {
            type string;
            description "IPv6 link-local address for next-hop (RFC 2545 Section 3)";
        }

        leaf local-as {
            type zt:asn;
            description "Local AS for this peer";
        }

        leaf peer-as {
            type zt:asn;
            mandatory true;
            description "Peer Autonomous System Number (required)";
        }

        leaf hold-time {
            type uint16 {
                range "0 | 3..65535";
            }
            default 90;
            description "Hold time in seconds (RFC 4271: 0 or >= 3)";
        }

        leaf connection {
            type enumeration {
                enum both { description "Initiate and accept connections (default)"; }
                enum passive { description "Accept only — do not initiate outbound"; }
                enum active { description "Initiate only — do not accept inbound"; }
            }
            default both;
            description "TCP connection establishment mode for this peer";
        }

        leaf port {
            type uint16 {
                range "1..65535";
            }
            description "Per-peer listen port (overrides global tcp.port for this peer)";
        }

        leaf group-updates {
            type boolean;
            default true;
            description "Group UPDATE messages";
        }

        // Address families
        list family {
            key "name";
            description "Address families to negotiate";
            leaf name {
                type string;
                ze:validate "registered-address-family";
                description "AFI/SAFI (e.g. ipv4/unicast)";
            }
            leaf mode {
                type enumeration {
                    enum enable { description "Enable this address family"; }
                    enum disable { description "Disable this address family"; }
                    enum require { description "Require this address family"; }
                    enum ignore { description "Ignore this address family"; }
                }
                description "Address family negotiation mode";
            }
        }

        // Capabilities
        container capability {
            description "BGP capability negotiation";

            leaf asn4 {
                type boolean;
                default true;
                description "4-byte ASN support (true/false/enable/disable/require/refuse)";
            }

            container route-refresh {
                presence "Route Refresh capability enabled";
                description "Route Refresh capability";
            }

            // NOTE: graceful-restart moved to GR plugin (ze-graceful-restart.yang)

            container add-path {
                presence "ADD-PATH capability enabled";
                description "ADD-PATH capability";
                leaf send {
                    type boolean;
                    default false;
                    description "Send ADD-PATH";
                }
                leaf receive {
                    type boolean;
                    default false;
                    description "Receive ADD-PATH";
                }
            }

            container extended-message {
                presence "Extended Message capability enabled";
                description "Extended Message capability";
            }

            list nexthop {
                key "family";
                description "Extended Next Hop capability (RFC 8950)";
                leaf family { type string; description "NLRI family (e.g. ipv4/unicast)"; }
                leaf nhafi { type string; description "Next-hop AFI (e.g. ipv6)"; }
                leaf mode {
                    type enumeration {
                        enum enable { description "Enable extended next hop"; }
                        enum disable { description "Disable extended next hop"; }
                        enum require { description "Require extended next hop"; }
                        enum refuse { description "Refuse extended next hop"; }
                    }
                    description "Extended next hop negotiation mode";
                }
            }

        }

        // Additional peer settings
        // NOTE: host-name/domain-name moved to hostname plugin (ze-hostname.yang)

        leaf md5-password {
            type string;
            description "MD5 authentication password";
        }

        leaf md5-ip {
            type zt:ip-address;
            description "MD5 authentication IP";
        }

        leaf ttl-security {
            type uint16;
            description "TTL security (GTSM)";
        }

        leaf outgoing-ttl {
            type uint16;
            description "Outgoing TTL";
        }

        leaf incoming-ttl {
            type uint16;
            description "Incoming TTL";
        }

        leaf manual-eor {
            type boolean;
            description "Manual End-of-RIB";
        }

        leaf auto-flush {
            type boolean;
            description "Auto-flush routes";
        }

        leaf adj-rib-out {
            type boolean;
            description "Maintain Adj-RIB-Out";
        }

        leaf adj-rib-in {
            type boolean;
            description "Maintain Adj-RIB-In";
        }

        // Native update syntax - Ze-native route announcements
        // update { attribute { origin igp; next-hop 10.0.0.1; } nlri { ipv4/unicast 1.0.0.0/24; } }
        list update {
            description "Native Ze route announcements";

            container attribute {
                description "Path attributes for routes in this block";
                leaf origin {
                    type enumeration {
                        enum igp { description "Interior Gateway Protocol"; }
                        enum egp { description "Exterior Gateway Protocol"; }
                        enum incomplete { description "Incomplete origin"; }
                    }
                    description "ORIGIN attribute (RFC 4271 Section 4.3)";
                }
                leaf next-hop { type string; description "Next hop address or 'self'"; }
                leaf med { type uint32; description "Multi-Exit Discriminator"; }
                leaf local-preference { type uint32; description "Local preference"; }
                leaf-list as-path { type string; description "AS path"; }
                leaf-list community { type string; description "Communities"; }
                leaf-list large-community { type string; description "Large communities"; }
                leaf-list extended-community { type string; description "Extended communities"; }
                leaf label { type string; description "MPLS label"; }
                leaf-list labels { type string; description "Multi-label stack (RFC 8277)"; }
                leaf path-information { type string; description "ADD-PATH path-id"; }
                leaf rd { type string; description "Route Distinguisher (RFC 4364)"; }
                leaf aggregator { type string; description "Aggregator AS:IP"; }
                leaf atomic-aggregate { type boolean; description "Atomic aggregate flag"; }
                leaf originator-id { type zt:ipv4-address; description "Originator ID"; }
                leaf-list cluster-list { type string; description "Cluster list"; }
                leaf-list attribute { type string; description "Generic hex attributes"; }
                container bgp-prefix-sid { presence "Prefix-SID enabled"; description "Prefix-SID (label index)"; }
                container bgp-prefix-sid-srv6 { presence "SRv6 Prefix-SID enabled"; description "SRv6 Prefix-SID"; }
                leaf split { type string; description "Prefix splitting"; }
            }

            list nlri {
                key "name";
                leaf name { type string; description "Address family (e.g., ipv4/unicast)"; }
                leaf content { type string; description "Operation, qualifiers, and payload"; }
            }

            container watchdog {
                description "Watchdog-controlled route - held until 'bgp watchdog announce <name>'";
                leaf name { type string; description "Watchdog group name"; }
                leaf withdraw { type boolean; description "Start in withdrawn state (default true)"; }
            }
        }

        // Per-family add-path configuration
        list add-path {
            key "family";
            description "Per-family ADD-PATH configuration (RFC 7911)";
            leaf family { type string; description "Address family (e.g. ipv4/unicast)"; }
            leaf direction {
                type enumeration {
                    enum send { description "Send ADD-PATH"; }
                    enum receive { description "Receive ADD-PATH"; }
                    enum send/receive { description "Both send and receive ADD-PATH"; }
                }
                description "ADD-PATH direction";
            }
            leaf mode {
                type enumeration {
                    enum enable { description "Enable ADD-PATH for this family"; }
                    enum disable { description "Disable ADD-PATH for this family"; }
                    enum require { description "Require ADD-PATH for this family"; }
                    enum refuse { description "Refuse ADD-PATH for this family"; }
                }
                description "ADD-PATH negotiation mode";
            }
        }

        // Process bindings
        list process {
            key "name";
            description "Process binding";

            leaf name {
                type string;
                description "Process name";
            }

            leaf run {
                type string;
                description "Command to execute";
            }

            // Old syntax fields
            leaf-list processes {
                type string;
                description "Process list";
            }

            leaf-list processes-match {
                type string;
                description "Process match patterns";
            }

            container neighbor-changes {
                presence "Neighbor change notifications enabled";
                description "Neighbor change notifications";
            }

            // New syntax fields
            container content {
                description "Content configuration";
                leaf encoding { type string; }
                leaf format { type string; }
                leaf attribute { type string; }
            }

            leaf-list receive {
                type enumeration {
                    enum all { description "All message types"; }
                    enum update { description "UPDATE messages"; }
                    enum open { description "OPEN messages"; }
                    enum notification { description "NOTIFICATION messages"; }
                    enum keepalive { description "KEEPALIVE messages"; }
                    enum refresh { description "ROUTE-REFRESH messages"; }
                    enum state { description "State change events"; }
                    enum sent { description "Sent messages"; }
                    enum negotiated { description "Negotiated capabilities"; }
                }
                description "Message types to receive";
            }

            leaf-list send {
                type enumeration {
                    enum all { description "All message types"; }
                    enum update { description "UPDATE messages"; }
                    enum refresh { description "ROUTE-REFRESH messages"; }
                    enum borr { description "Beginning of Route Refresh (RFC 7313)"; }
                    enum eorr { description "End of Route Refresh (RFC 7313)"; }
                }
                description "Message types to send";
            }
        }

        // RIB configuration
        container rib {
            description "RIB configuration";
            container out {
                description "Outbound RIB settings";
                leaf group-updates {
                    type boolean;
                    default true;
                    description "Group updates";
                }
                leaf auto-commit-delay {
                    type string;
                    default "0";
                    description "Auto-commit delay";
                }
                leaf max-batch-size {
                    type int32;
                    default 0;
                    description "Max batch size";
                }
            }
        }

    }
}
