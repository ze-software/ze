module ze-mrt-conf {
    namespace "urn:ze:mrt:conf";
    prefix mrt;

    import ze-extensions { prefix ze; }

    description "MRT routing information export configuration (RFC 6396)";

    revision 2026-06-07 {
        description "Initial revision";
    }

    grouping dump-stream-settings {
        description "Common settings for an MRT dump stream";

        leaf file {
            type string {
                length "1..255";
            }
            description "The strftime codes in the path decide when Ze opens a new file.
                         The supported codes are %Y (year), %m (month), %d (day),
                         %H (hour), %M (minute), %S (second), %s (unix timestamp) and
                         %N (table name).";
            ze:help
                "Output file path, with strftime patterns for rotation.";
        }

        leaf interval {
            type uint32 {
                range "0..86400";
            }
            default 0;
            description
                "The value 0 keeps one file open until the daemon stops.
                 A value of more than 0 makes Ze close the file once it has been open
                 that many seconds. Ze then opens the next one, and the strftime codes
                 in file give the new name. A file of -
                 writes to standard output, which never rotates.";
            ze:help "File rotation interval in seconds. Zero disables rotation.";
        }
    }

    container mrt {
        description "The container holds the extended-timestamp switch, the add-path
                     switch, the peer filter, the direction, and the three dump streams.";
        ze:help "MRT dump configuration.";

        leaf extended-timestamp {
            type boolean;
            default false;
            description
                "The default is false, so each record header carries type 16, BGP4MP.
                 RFC 6396 Section 5.3 names type 17 as BGP4MP_ET, and that header
                 carries 4 more bytes for the microsecond field. The switch reaches all
                 three streams at once.";
            ze:help "Use BGP4MP_ET (type 17) with microsecond resolution
                     instead of BGP4MP (type 16).";
        }

        leaf add-path {
            type boolean;
            default false;
            description
                "The default is false. When true, TABLE_DUMP_V2 snapshots use
                 the ADD-PATH RIB subtypes of RFC 8050. BGP4MP and BGP4MP_ET
                 message subtypes always follow the direction-specific negotiated
                 ADD-PATH state of the UPDATE family, independently of this leaf.";
            ze:help "Use ADD-PATH subtypes for RIB snapshots.";
        }

        leaf-list peer-filter {
            type string;
            description
                "Ze compares each entry with the peer address of the message, so a
                 message of another peer reaches no file. The filter reaches the BGP
                 messages alone: Ze writes a state change record for every peer,
                 whatever this list holds.";
            ze:help "If set, only record messages from/to these peer addresses.
                     Empty list means record all peers.";
        }

        leaf direction {
            type enumeration {
                enum both { ze:help "Record the BGP messages of each direction."; }
                enum received { ze:help "Record the BGP messages the peer sent to Ze alone."; }
                enum sent { ze:help "Record the BGP messages Ze sent to the peer alone."; }
            }
            default both;
            description
                "The default is both, and both records each direction. received keeps
                 the messages the peer sent to Ze, and sent keeps the messages Ze sent
                 to the peer. The filter reaches the BGP messages alone, so a state change record is written
                 whatever the value.";
            ze:help "Which direction of BGP messages to record.";
        }

        container updates {
            description "The stream carries the UPDATE messages alone. The all stream
                         beside it carries every message type.";
            ze:help "BGP UPDATE message stream (BGP4MP records).";

            uses dump-stream-settings;
        }

        container all {
            description "The stream carries every BGP message: OPEN, UPDATE,
                         NOTIFICATION, KEEPALIVE and ROUTE_REFRESH. It carries the FSM
                         state transitions too. Ze writes them as BGP4MP records.";
            ze:help
                "All BGP messages and state changes, written as BGP4MP records.";
            uses dump-stream-settings;
        }

        container routes {
            description "Each dump writes one PEER_INDEX_TABLE record, and then the RIB
                         entries for every address family. Ze writes them as
                         TABLE_DUMP_V2 records.";
            ze:help
                "Periodic RIB snapshots, written as TABLE_DUMP_V2 records.";


            leaf file {
                type string {
                    length "1..255";
                }
                description
                    "The strftime codes in the path name the file Ze opens, exactly as
                     they do in a dump stream. Ze writes this stream only when the path is set
                     and interval is more than 0. A path of - writes to standard
                     output.";
                ze:help "Output file path with strftime patterns.";
            }

            leaf interval {
                type uint32 {
                    range "60..86400";
                }
                default 3600;
                description
                    "The default is 3600 seconds and the range is 60 to 86400. Each dump
                     writes one PEER_INDEX_TABLE record and then the RIB entries of
                     every address family, which RFC 6396 Section 4.3.1 requires in that
                     order.";
                ze:help "RIB dump interval in seconds. Minimum 60.";
            }
        }
    }
}
