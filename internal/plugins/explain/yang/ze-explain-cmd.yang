module ze-explain-cmd {
    namespace "urn:ze:explain:cmd";
    prefix explaincmd;
    import ze-extensions { prefix ze; }
    description "The show diagnostic command, owned by the explain plugin, which registers its handler. See the plugin self-containment rule.";
    revision 2026-10-12 { description "Rename explain to show diagnostic: the first word of a command is its verb."; }
    revision 2026-10-08 { description "Initial: declare the explain command the explain plugin already served."; }

    container show {
        config false;
        ze:help "Read-only commands to inspect system, protocol, and network state.";

        container diagnostic {
            config false;
            ze:command "ze-explain:show-diagnostic";
            description "The answer gives the meaning of the code, its likely cause and the recommended
fix. It is read from the diagnostic catalog this binary carries and asks no daemon.";
            ze:help "Explain one diagnostic code Ze printed.";
            leaf code {
                type string { length "1..64"; }
                mandatory true;
                description "A diagnostic code as a log line or an error message printed it. An unknown
code is refused.";
                ze:help "Diagnostic code.";
            }
        }
    }
}
