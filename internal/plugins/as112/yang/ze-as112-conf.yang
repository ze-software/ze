module ze-as112-conf {
    namespace "urn:ze:as112:conf";
    prefix as112;

    import ze-types { prefix zt; }
    import ze-extensions { prefix ze; }

    description
        "AS112 anycast DNS node configuration for Ze: authoritative sink for
         misdirected RFC 1918 / link-local reverse-DNS queries (RFC 7534) and
         the EMPTY.AS112.ARPA DNAME-redirection sink (RFC 7535). The four
         anycast host addresses and every served zone are fixed -- no
         operator-typed IP address anywhere in this module.";

    revision 2026-07-05 {
        description
            "Add asn, community, and watchdog leaves so the fixed AS112 covering
             prefixes can be originated into BGP via redistribute (import
             as112), health-gated on DNS serving state (RFC 7534 Section 3.3).";
    }

    revision 2026-07-01 {
        description "Initial revision";
    }

    container service {
        description "The container holds the settings of each service Ze runs, and the
                     as112 container under it configures the AS112 node.";
        ze:help "Service settings.";

        container as112 {
            description "The container holds the enable switch, the address family, the
                         node identification strings, the access list, the BGP settings
                         and the secure listeners.";
            ze:help "AS112 anycast DNS node.";

            leaf enabled {
                type boolean;
                default false;
                description "The AS112 node does not start while this leaf is false, and
                             false is the default.";
                ze:help "Enable the AS112 anycast DNS node.";
            }

            leaf address-family {
                type enumeration {
                    enum both {
                        ze:help "Serve on both IPv4 and IPv6 anycast addresses. This is the default.";
                    }
                    enum ipv4-only {
                        ze:help "Serve on the two IPv4 anycast addresses only.";
                    }
                    enum ipv6-only {
                        ze:help "Serve on the two IPv6 anycast addresses only.";
                    }
                }
                default "both";
                description
                    "RFC 7534 Section 3.4 and RFC 7535 Section 3.1 give the
                     single-stack option. The anycast addresses themselves are
                     fixed constants, and an operator never types one.";
                ze:help
                    "Restrict the service to one address family.";
            }

            leaf hostname {
                type string {
                    length "0..63";
                }
                description
                    "RFC 7534 Section 3.5 defines those answers. The string tells
                     an operator which anycast instance answered a query. An empty
                     value omits the TXT string.";
                ze:help
                    "Node identification string in the HOSTNAME.AS112.NET/ARPA TXT answers.";
            }

            leaf facility {
                type string {
                    length "0..100";
                }
                description
                    "The facility name is the name of the site, for example
                     'Example Datacenter'. It is surfaced beside the location.";
                ze:help
                    "Facility name in the HOSTNAME.AS112.NET/ARPA TXT answers.";
            }

            leaf location {
                type string {
                    length "0..100";
                }
                description
                    "The location is surfaced beside the facility, for example
                     'London, UK'.";
                ze:help
                    "City and country in the HOSTNAME.AS112.NET/ARPA TXT answers.";
            }

            leaf-list allow-from {
                type zt:ip-prefix;
                description
                    "An empty list, which is the default, answers every source and
                     matches the standard AS112 public-sink behavior. With one
                     prefix or more, the node answers a query only when its source
                     IP is inside one of those prefixes. It drops every other query
                     and sends no response.
                     A loopback source and an on-box source are always permitted,
                     whatever this list holds, so the 'request as112 healthcheck'
                     probe is never blocked.
                     A set list makes the node non-public. That is correct for a
                     local-use mirror, and wrong for an AS112 contributor the whole
                     internet reaches.";
                ze:help
                    "Client-source access list of the queries the node answers.";
            }

            leaf asn {
                type zt:asn;
                default 112;
                description
                    "The redistribute statement is `redistribute { destination bgp
                     { import as112 } }`. The default is the well-known AS112
                     number 112 (RFC 7534 Section 3.2), because the redistribute
                     source models an AS112 virtual router. Set an operator ASN, or
                     an RFC 6996 private-use ASN, to originate under a coordinated
                     AS or a local-use AS instead. Ze ignores this leaf unless
                     'import as112' is configured under redistribute.";
                ze:help
                    "Origin AS the AS112 covering prefixes carry when redistributed into BGP.";
            }

            leaf-list community {
                type string;
                max-elements 32;
                description
                    "The leaf takes an AA:NN standard community (RFC 1997) and a
                     well-known name such as no-export or nopeer (RFC 3765). Those
                     are the values RFC 7534 Section 3.4 recommends to restrict
                     AS112 route propagation.
                     The type is 'string' rather than the AA:NN-only ze-types
                     community pattern, so a well-known name is accepted. The
                     canonical community parser validates every value at config
                     time. Ze ignores this leaf unless 'import as112' is configured
                     under redistribute.";
                ze:help
                    "BGP communities attached to the redistributed AS112 covering prefixes.";
            }

            leaf watchdog {
                type boolean;
                default true;
                description
                    "RFC 7534 Section 3.3 states that a node does not advertise the
                     service prefix while the name server is not running. With true,
                     which is the default, Ze announces the covering prefixes only
                     while the as112 node serves. Ze withdraws them when serving is
                     lost, when the service is disabled, and when the node shuts
                     down. With false, Ze announces as soon as the node is enabled
                     and imported, with no serving-state gate. Ze ignores this leaf
                     unless 'import as112' is configured under redistribute.";
                ze:help
                    "Announce the covering prefixes only while the node serves DNS.";
            }

            container tls {
                description
                    "RFC 7858 defines DNS-over-TLS (DoT). When it is enabled, the
                     DoT listener binds the fixed anycast addresses and the
                     loopback address on 'listen-port'.
                     When cert-file and key-file are both unset, Ze uses an
                     ephemeral self-signed certificate, which a strict client
                     cannot validate. Supply an operator PEM file for a node the
                     public trusts.";
                ze:help
                    "DNS-over-TLS listener, and the certificate material it shares with DoH.";

                leaf enabled {
                    type boolean;
                    default false;
                    description "The default is false. Ze binds DoT on every IP the cleartext
                                 listeners use, on listen-port. DoT is TCP only, because RFC
                                 7858 Section 3.1 defines no UDP counterpart. When the TLS
                                 material fails to load, Ze starts no secure listener and the
                                 cleartext listeners keep running.";
                    ze:help "Enable the DNS-over-TLS listener (RFC 7858).";
                }

                leaf listen-port {
                    type zt:port;
                    default 853;
                    description
                        "The RFC 7858 well-known 'domain-s' port is 853.";
                    ze:help
                        "TCP port for the DoT listener.";
                }

                leaf cert-file {
                    type string;
                    description
                        "When this leaf and key-file are both unset, Ze uses an
                         ephemeral self-signed certificate.";
                    ze:help
                        "Path to the PEM server certificate presented on DoT and DoH.";
                }

                leaf key-file {
                    type string;
                    ze:sensitive;
                    description
                        "Ze reads cert-file and key-file on each apply, so a rotated
                         pair reaches the listener without a restart. One of the two
                         alone stops the secure listeners with an error, and the
                         cleartext listeners keep running. The certificate leaf names a
                         PKI store entry instead, and Ze refuses a config that writes
                         both sources.";
                    ze:help "Path to the PEM private key matching cert-file. Must be
                             set together with cert-file.";
                }

                leaf certificate {
                    ze:reference "pki-certificate";
                    type string {
                        length "1..255";
                        pattern '[A-Za-z0-9._-]+';
                    }
                    description
                        "The listeners send the leaf certificate and every
                         intermediate certificate the store entry holds.
                         This leaf excludes cert-file and key-file. Setting both is
                         a configuration error.
                         The PKI store lives in the hub process, so a geodns plugin
                         or an as112 plugin started as an external process cannot
                         resolve the name. The secure listeners then do not start,
                         and Ze logs the error. Cleartext DNS still runs.";
                    ze:help
                        "Name of the PKI store certificate served on DoT and DoH.";
                }
            }

            container doh {
                description
                    "The listener reuses the certificate material of the tls
                     container. It binds the fixed anycast addresses and the
                     loopback address on 'listen-port', at 'path'.";
                ze:help
                    "DNS-over-HTTPS listener (RFC 8484).";

                leaf enabled {
                    type boolean;
                    default false;
                    description "The default is false. Ze binds DoH on every IP the cleartext
                                 listeners use, on listen-port, at path. The listener drives the
                                 same handler as cleartext DNS, so allow-from answers a DoH
                                 client exactly as it answers a UDP client. A query the handler
                                 refuses gets HTTP 403.";
                    ze:help "Enable the DNS-over-HTTPS listener (RFC 8484).";
                }

                leaf listen-port {
                    type zt:port;
                    default 443;
                    description "The default is 443, and the range is 1 to 65535. Ze refuses a
                                 port of 0. A GET carries the query base64url-encoded in the dns
                                 parameter, and a POST carries it in an application/dns-message
                                 body of 65535 bytes at most.";
                    ze:help "TCP port for the DoH HTTPS listener (RFC 8484).";
                }

                leaf path {
                    type string;
                    default "/dns-query";
                    description
                        "RFC 8484 defines the URI Template. The default path is
                         /dns-query.";
                    ze:help
                        "HTTP request path the DoH endpoint answers on.";
                }
            }

            // Schema anchors for cross-service port-conflict detection
            // (finding L3): these two lists sit directly under container
            // as112 (NOT inside a wrapper container) because a `config
            // false` container with zero operator-typeable content never
            // materializes in the parsed config Tree (empirically verified:
            // internal/component/config's tree walk stops at the first
            // GetContainer() that returns nil), which silently made the
            // former ipv4-anycast/ipv6-anycast wrapper-container shape a
            // permanent no-op regardless of RegisterListenerDefault calls.
            // container as112 itself always materializes once `enabled` is
            // committed, so anchoring the lists there -- one level up --
            // fixes materialization. As a side effect the derived
            // listenerService now inherits as112's "enabled" leaf as its
            // gate (hasEnabledLeaf=true, matching geodns's own listener
            // gating precedent): the conflict check only fires while as112
            // is actually enabled, which is the correct semantic (a
            // disabled service is not occupying the port).
            list ipv4-anycast-listener {
                key "name";
                config false;
                ze:listener;
                description
                    "as112 always occupies port 53 on its fixed IPv4 anycast
                     addresses while it is enabled. The Go-level default,
                     RegisterListenerDefault, fills in the representative address,
                     because no operator-facing command populates this list.";
                ze:help
                    "Presence-only anchor for port 53 on the fixed IPv4 anycast addresses.";

                leaf name {
                    type string;
                    description "The name is the list key. No operator-facing command
                                 writes this list, so it carries one fixed entry.";
                    ze:help "Fixed entry name.";
                }

                uses zt:listener {
                    refine ip {
                        default "192.175.48.1";
                    }
                    refine port {
                        default 53;
                    }
                }
            }

            list ipv6-anycast-listener {
                key "name";
                config false;
                ze:listener;
                description
                    "as112 always occupies port 53 on its fixed IPv6 anycast
                     addresses while it is enabled.";
                ze:help
                    "Presence-only anchor for port 53 on the fixed IPv6 anycast addresses.";


                leaf name {
                    type string;
                    description "The name is the list key. No operator-facing command
                                 writes this list, so it carries one fixed entry.";
                    ze:help "Fixed entry name.";
                }

                uses zt:listener {
                    refine ip {
                        default "2620:4f:8000::1";
                    }
                    refine port {
                        default 53;
                    }
                }
            }
        }
    }
}
