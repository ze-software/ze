module ze-as112-cmd {
    namespace "urn:ze:as112:cmd";
    prefix as112cmd;

    import ze-extensions { prefix ze; }

    description
        "show as112 and request as112 healthcheck command tree. Owned by the
         as112 plugin because both handlers read the as112 server's live state.
         See ai/rules/plugin-self-containment.md.";

    revision 2026-07-01 {
        description "Initial revision";
    }

    container show {
        config false;
        ze:help "Read-only commands to inspect system, protocol, and network state.";

        container as112 {
            config false;
            ze:command "ze-as112:show-as112";
            description "Enabled, address-family, hostname/facility/location, allow-from count,
served zone count, and the current SOA serial.";
            ze:help "AS112 node status.";
        }
    }

    container request {
        config false;

        container as112 {
            config false;
            description "AS112 answers reverse-DNS queries for private address space, so these act on a
                         sink service rather than on a routing session.";
            ze:help "AS112 operational actions.";

            container healthcheck {
                config false;
                ze:command "ze-as112:health";
                description "The query goes to an anycast service address, or to the
given target. The exit code is 0 only when the expected AS112 answer comes
back. Finding M4: the tool a healthcheck probe calls, since dig is not on the
gokrazy appliance and 'ze resolve dns' cannot target a specific server.";
                ze:help "Send one authoritative query and check the AS112 answer.";

                leaf target {
                    type string;
                    description "An IP address, queried on port 53. When it is absent the query
goes to the on-box loopback of the configured address family: 127.0.0.1, or ::1 when
address-family is ipv6-only.";
                    ze:help "Anycast service address to query.";
                }
            }
        }
    }
}
