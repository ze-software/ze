module ze-traffic-usage-conf {
    namespace "urn:ze:traffic-usage:conf";
    prefix trafficusageconf;

    import ze-traffic-control-conf { prefix tc; }
    import ze-extensions { prefix ze; }

    description "eBPF TCX per-port and per-IP byte accounting configuration.
                 Augments the shared `traffic` container (owned by
                 ze-traffic-control-conf) with the `usage` subtree.";
    revision 2026-07-02 { description "Nest under traffic/usage: augment /tc:traffic with container usage."; }
    revision 2026-06-24 { description "Initial revision."; }

    augment "/tc:traffic" {
        container usage {
            description "Ze attaches two eBPF programs to each accounted interface with TCX, one on
                ingress and one on egress. They count bytes into per-interface LRU hash maps, keyed
                by L4 port and protocol. Where track-ip is true they also key by IPv4 address. One
                poll loop reads the maps and publishes the counts as metric series. The programs
                count only: they drop no packet and they change none.";
            ze:help "Per-interface eBPF TCX byte accounting (port/protocol always; per-IP via track-ip).";

            leaf enabled {
                type boolean;
                default false;
                description "The default false attaches nothing and starts no poll loop. Set it true and
                    the config also needs one enabled interface or more under interfaces. Without
                    one, the commit is refused and the error names the missing interface list. An accounting
                    that would report nothing never reaches the kernel.";
                ze:help "Enable traffic-usage accounting.";
            }

            container interfaces {
                description "Ze accounts on the interfaces listed here and on no other. An interface
                    with no entry is not accounted, and an entry whose enabled leaf is false is
                    dropped before the attach. With usage enabled and this list empty, the commit is
                    refused.";
                ze:help "Interfaces to account on.";
                list interface {
                    key "name";
                    description "The entry names one interface and can override three leaves of the
                        usage container: track-ip, stale-timeout and max-entries. What the entry
                        does not set, it takes from the leaf of the same name under usage. An entry
                        with a name and no body is accounted with every global value. A change to
                        track-ip or to max-entries makes Ze detach the eBPF programs and attach them
                        again, because both decide the shape of the maps.";
                    ze:help "Per-interface traffic-usage accounting.";
                    leaf name {
                        type string {
                            length "1..255";
                            pattern '[A-Za-z0-9][A-Za-z0-9._@-]*';
                        }
                        description "Ze resolves the name to its kernel device before the accounting attaches to that device. The
                            resolution honors the os-name selector and the mac-match selector.";
                        ze:help "Ze interface name that this accounting entry counts bytes for.";
                    }
                    leaf enabled {
                        type boolean;
                        default true;
                        description "The default true accounts on the interface, so an entry with no
                            body needs nothing more. Set it false and Ze drops the entry before it
                            attaches anything. The accounting on that interface stops, and the rest
                            of the list is not touched. To stop the whole feature, use the enabled
                            leaf under usage.";
                        ze:help "Account traffic on this interface.";
                    }
                    leaf track-ip {
                        type boolean;
                        description "The leaf overrides the track-ip leaf under usage for this interface
                            alone, and an unset leaf takes the global value. True adds two more LRU
                            maps to this interface, one for ingress and one for egress, keyed by
                            IPv4 address. A change makes Ze attach the eBPF programs again, because
                            the map set changes.";
                        ze:help "Override the global track-ip for this interface (inherits the global value when unset).";
                    }
                    leaf stale-timeout {
                        type uint32;
                        description "0 disables the cleanup for this interface. When the leaf is unset, this interface inherits the
                            global stale-timeout.";
                        ze:help "Override the global stale-timeout for this interface, in milliseconds.";
                    }
                    leaf max-entries {
                        type uint32 {
                            range "1..4294967295";
                        }
                        description "The leaf overrides the max-entries leaf under usage for this
                            interface alone, and an unset leaf takes the global value. The value is
                            the capacity of each LRU map of the interface, so it also sets the
                            memory the interface costs. An effective value of 0 is refused at
                            commit. A change makes Ze attach the eBPF programs again, because a map
                            takes its capacity at creation.";
                        ze:help "Override the global max-entries (per-map LRU capacity) for this interface (inherits when unset).";
                    }
                }
            }

            leaf interval {
                type uint32 {
                    range "100..3600000";
                }
                default 1000;
                description "One poll loop reads every map of every accounted interface at this period,
                    so the value sets how fresh a metric series is. The default 1000 reads once a
                    second. A value outside 100 milliseconds to 1 hour is refused at commit. The
                    eBPF programs count at line rate whatever this value is, so a longer interval
                    loses no bytes.";
                ze:help "Map poll interval in milliseconds (100ms..1h).";
            }

            leaf stale-timeout {
                type uint32;
                default 300000;
                description "Ze removes a metric series it has not seen within this time, which stops
                    the series of a talker that left from staying forever. The value 0 disables the
                    cleanup, so every series stays until the plugin stops. An interface can
                    override the value with its own stale-timeout leaf. An interface value that is
                    not 0 and less than 1 second is refused at commit.";
                ze:help "Remove a metric series unseen within this many milliseconds; 0 disables cleanup.";
            }

            leaf track-ip {
                type boolean;
                default false;
                description "The address is the source address on ingress and the destination address on egress. The default is
                    false, which limits the number of metric series.";
                ze:help "Account bytes per IPv4 address as well as per interface.";
            }

            leaf max-entries {
                type uint32 {
                    range "1..4294967295";
                }
                default 10240;
                description "The value is the capacity of each LRU map, and an interface takes it unless
                    its own max-entries leaf overrides it. Ze creates two maps for each accounted
                    interface, and two more where track-ip is true, so the value sets the memory the
                    accounting costs. Beyond the capacity the kernel evicts the least recently used
                    entry, which keeps the top talkers and loses the quiet ones.";
                ze:help "Per-map LRU capacity; least-recently-used entries are evicted beyond this, keeping top talkers.";
            }
        }
    }
}
