module ze-traffic-usage-cmd {
    namespace "urn:ze:traffic-usage:cmd";
    prefix trafficusagecmd;
    import ze-extensions { prefix ze; }
    description "show traffic usage command tree. Owned by the traffic-usage plugin so that removing the plugin removes the command node together with its handler. Container-merges onto the shared `traffic` namespace. See ai/rules/plugin-self-containment.md.";
    revision 2026-07-02 { description "Nest under show traffic usage (was show traffic-usage)."; }
    revision 2026-06-24 { description "Initial: show traffic-usage displays per-interface eBPF byte counters."; }

    container show {
        config false;
        ze:help "Read-only commands to inspect system, protocol, and network state.";

        container traffic {
            config false;
            ze:help "Traffic subsystem: QoS control and byte-usage accounting.";

            container usage {
                config false;
                ze:command "ze-trafficusage:show-traffic-usage";
                description "Per destination/source port and protocol counters are always present; per-IP
top-talker counters appear when track-ip is enabled. Without arguments, lists
all monitored interfaces. With 'name <interface>', shows that one interface.";
                ze:help "Show per-interface traffic byte counters captured by eBPF TCX.";
                leaf name {
                    type string;
                    description "The kernel interface name, as configured under traffic usage. An
interface the plugin does not monitor fails with interface not monitored.";
                    ze:help "Interface name (used with 'name <interface>')";
                }
            }
        }
    }
}
