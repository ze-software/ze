module ze-vrrp-cmd {
    namespace "urn:ze:vrrp:cmd";
    prefix vrrpcmd;

    import ze-extensions    { prefix ze; }
    import ze-types         { prefix zt; }
    import ze-cli-show-cmd  { prefix clishowcmd; }
    import ze-cli-clear-cmd { prefix cliclearcmd; }

    description
        "VRRP operational commands: virtual-router state, per-interface detail,
         counters, and a counter reset. Owned by the vrrp plugin so that deleting
         the plugin removes the commands, their schema, and their handlers
         together (ai/rules/plugin-self-containment.md). The wire methods these
         nodes bind are registered in cmd_show.go as plugin proxies.";

    revision 2026-10-17 {
        description "clear vrrp statistics alone is refused; clear vrrp statistics all zeroes every virtual router.";
    }
    revision 2026-07-15 {
        description "Initial revision (spec-vrrp-5).";
    }

    augment "/clishowcmd:show" {
        container vrrp {
            config false;
            ze:command "ze-vrrp:show-vrrp";
            description "Per router: its group name, VRID, address family, state (initialize,
backup, master), configured and effective priority, virtual addresses, and the
macvlan device that carries the virtual MAC.";
            ze:help "Show every VRRP virtual router.";

            container interface {
                config false;
                description "One interface can host several virtual routers. Each one has its own
                             VRID and its own election. This view can therefore report more than
                             one state for one link.";
                ze:help "Show the VRRP virtual routers hosted on one interface.";

                container name {
                    config false;
                    ze:command "ze-vrrp:show-interface";
                    description "Pass the interface name: show vrrp interface name <interface>.";
                    ze:help "Show the VRRP virtual routers on one parent interface.";

                    leaf value {
                        type zt:node-name;
                        description "The name of the parent interface whose virtual routers the answer lists.
The word after the name keyword is the value, and a bare word with no keyword is
accepted from a programmatic sender.";
                        ze:help "Parent interface name";
                    }
                }
            }

            container statistics {
                config false;
                ze:command "ze-vrrp:show-statistics";
                description "Advertisements sent and received, priority-zero advertisements,
gratuitous ARP and unsolicited neighbor advertisement bursts,
receive-validation errors by reason, and the derived skew and master-down
timers in microseconds (a VRRPv3 skew is sub-millisecond).";
                ze:help "Show per-virtual-router counters.";
            }
        }
    }

    augment "/cliclearcmd:clear" {
        container vrrp {
            config false;
            description "Only the counters are zeroed. The election is untouched, so a master stays master
                         and no failover is provoked by clearing them.";
            ze:help "Reset VRRP runtime counters.";

            container statistics {
                config false;
                description "clear vrrp statistics alone is refused: say all to zero every virtual
router's counters. Everything is never the default.";
                ze:help "Reset VRRP counters: all.";

                container all {
                    config false;
                    ze:command "ze-vrrp:clear-statistics";
                    description "Protocol state is untouched: clearing counters never triggers a failover.";
                    ze:help "Reset every VRRP virtual router's counters to zero.";
                }
            }
        }
    }
}
