module ze-vrrp-conf {
    namespace "urn:ze:vrrp:conf";
    prefix vrrp;

    import ze-types { prefix zt; }
    import ze-extensions { prefix ze; }
    import ze-iface-conf { prefix iface; }

    description
        "VRRP (Virtual Router Redundancy Protocol) configuration for Ze:
         RFC 9568 (VRRPv3, default) and RFC 3768 (VRRPv2, opt-in for IPv4).
         Attaches under an interface unit's ipv4/ipv6 container as
         `vrrp { group <vrid> { ... } }`. The vrrp container carries
         ze:backend \"netlink\" so the iface backend gate rejects it under a
         VPP-backed interface tree until native VPP VRRP lands (spec-vrrp-7).
         VRID namespaces are independent per family (RFC 9568 separate virtual
         routers). Cross-leaf constraints (interval-vs-version, IPv6 first-VIP
         link-local, owner detection, duplicate-VIP) live in the plugin
         verifier, not per-leaf, because they need sibling context.";

    revision 2026-07-15 {
        description "Initial revision (spec-vrrp-5).";
    }

    grouping vrrp-group-ipv4 {
        description "VRRP groups on an IPv4 interface unit (RFC 9568 / RFC 3768).";

        container vrrp {
            ze:backend "netlink";
            description "Ze runs each group as its own state machine, on a macvlan
                         device that carries the group's virtual MAC. The device name
                         starts with zv4 and takes the parent ifindex and the VRID,
                         inside the 15-character kernel limit. The container carries
                         ze:backend netlink, so a tree with interface backend vpp is
                         refused at verify with \"VRRP requires the netlink interface
                         backend\". A VRID is unique for one unit and one family, so
                         the same VRID CAN run on the IPv6 unit beside it.";
            ze:help "VRRP virtual routers hosted on this IPv4 unit.";

            list group {
                key "name";
                description "The name is a config label only, and Ze never sends it on
                             the wire. The VRID leaf carries the protocol identity.";
                ze:help "One virtual router, identified by an operator-assigned name.";

                leaf name {
                    type zt:node-name;
                    description "Ze keys the running instance on interface, unit, family
                                 and this name. So a change to vrid reconfigures the
                                 same virtual router, and a change to the name removes
                                 one virtual router and creates another. The name is 1
                                 to 255 characters of letters, digits, underscore,
                                 hyphen and dot. The first character MUST be a letter, a
                                 digit or an underscore. Every VRRP error message opens
                                 with the name, because the operator typed it.";
                    ze:help "Config-level group name (free-form label, used as list key).
                             Not sent on the wire.";
                }

                leaf vrid {
                    type uint8 {
                        range "1..255";
                    }
                    mandatory true;
                    description "The VRID is unique per interface unit and per address
                                 family. The IPv4 VRID space and the IPv6 VRID space
                                 are independent.";
                    ze:help "Virtual Router Identifier (RFC 9568 Section 5.2.3).";
                }

                leaf-list virtual-address {
                    type zt:ipv4-address;
                    min-elements 1;
                    max-elements 16;
                    ze:syntax "bracket";
                    description "RFC 9568 Section 5.2.9 sets the wire order, which is
                                 the configuration order. An address equal to a real
                                 address on this unit makes this router the owner. Ze
                                 then forces the priority to 255, and forces
                                 accept-mode to true.";
                    ze:help "Virtual IPv4 addresses, encoded on the wire in configuration order.";
                }

                leaf priority {
                    type uint8 {
                        range "1..254";
                    }
                    default 100;
                    description "255 is reserved for the address owner, and Ze assigns
                                 it automatically. An operator never sets it.";
                    ze:help "Election priority (RFC 9568 Section 5.2.4).";
                }

                leaf preempt {
                    type boolean;
                    default "true";
                    description "A Backup router with a higher priority takes over from
                                 a live Active router with a lower priority.";
                    ze:help "Preempt_Mode (RFC 9568 Section 6.4.2).";
                }

                leaf preempt-delay-seconds {
                    type uint16 {
                        range "0..3600";
                    }
                    default 0;
                    description "RFC 9568 does not define this hold-time. Ze arms it on
                                 the first losing advertisement while a local router
                                 with a higher priority waits. It never delays failover
                                 from a dead Active router.";
                    ze:help "Preemption hold-time, in Junos semantics.";
                }

                leaf advertise-interval-milliseconds {
                    type uint32 {
                        range "10..255000";
                    }
                    default 1000;
                    description "The native range spans both versions, and the plugin
                                 verifier narrows it per version. Version 3 takes
                                 multiples of 10 ms within 10..40950, and the wire
                                 carries centiseconds (RFC 9568 erratum 8301). Version
                                 2 takes whole seconds within 1000..255000, and the
                                 wire carries seconds.";
                    ze:help "Advertisement interval in milliseconds.";
                }

                leaf version {
                    type enumeration {
                        enum "2" {
                            value 2;
                            ze:help "RFC 3768 (VRRPv2), IPv4 only, auth type 0 only.";
                        }
                        enum "3" {
                            value 3;
                            ze:help "RFC 9568 (VRRPv3).";
                        }
                    }
                    default "3";
                    description "The leaf is present only for an IPv4 group. An IPv6
                                 group is always VRRPv3 (RFC 9568).";
                    ze:help "Protocol version.";
                }

                leaf checksum {
                    type enumeration {
                        enum "rfc9568" {
                            ze:help "Checksum over the VRRP message alone (RFC 9568 Section 5.2.8).";
                        }
                        enum "rfc5798-compatible" {
                            ze:help "Checksum over the IPv4 pseudo-header and the message, as keepalived sends.";
                        }
                    }
                    default "rfc9568";
                    description "Selects the VRRPv3 IPv4 checksum form. The group sends
                                 and accepts only that form, and an advertisement in
                                 the other form is dropped and counted as a checksum
                                 error. RFC 9568 computes the IPv4 checksum over the
                                 VRRP message alone. RFC 5798 also covered an IPv4
                                 pseudo-header, and keepalived and other pre-RFC 9568
                                 routers still send and require that form, so a group
                                 sharing a segment with them needs rfc5798-compatible.
                                 Such a group also keeps the RFC 5798 owner rule: its
                                 address owner discards every advertisement it
                                 receives, where an rfc9568 owner logs and processes it.
                                 Version 2 always sums the message alone and refuses
                                 rfc5798-compatible. IPv6 groups have no such leaf:
                                 both RFCs cover the IPv6 pseudo-header.";
                    ze:help "VRRPv3 IPv4 checksum form: rfc9568 or rfc5798-compatible.";
                }

                leaf accept-mode {
                    type boolean;
                    default "false";
                    description "A non-owner Active router accepts packets addressed to
                                 the virtual addresses. The leaf carries version 3
                                 semantics only, and the plugin verifier rejects true
                                 beside version 2.
                                 The dataplane enforces the leaf. With false on a
                                 non-owner, the router still answers ARP and Neighbor
                                 Discovery for the virtual addresses, and still
                                 forwards for the virtual MAC. It does not accept
                                 packets addressed to them, so a ping to a virtual
                                 address gets no reply. The address owner accepts
                                 whatever this leaf says.";
                    ze:help "Accept_Mode (RFC 9568 Sections 6.1 and 6.4.3).";
                }

                container track {
                    description "Ze sums the priority-decrement of every tracked
                                 interface that is down, and subtracts the sum from
                                 the configured priority. The result never falls
                                 below 1 (RFC 9568 Section 5.2.4), and Ze advertises
                                 the new priority at once. Tracking is refused on the
                                 group that owns its virtual address, because that
                                 group advertises 255 whatever a decrement says.";
                    ze:help "Interfaces whose loss lowers the priority this group advertises.";

                    list interface {
                        key "name";
                        max-elements 16;
                        description "Ze reads the interface's operational state only,
                                     so this interface does not need an address of
                                     the group's family. Two interfaces that are down
                                     cost the sum of their decrements.";
                        ze:help "One tracked interface and the priority its loss costs.";

                        leaf name {
                            type zt:node-name;
                            ze:validate "vrrp-track-interface";
                            description "Ze resolves the name through the resolver
                                         show interface uses, so a kernel device the
                                         interface tree does not carry still
                                         resolves. A name that resolves to no device
                                         counts as DOWN, and Ze logs the resolver
                                         error at warn.";
                            ze:help "Interface to watch, by interface-tree name or kernel device name.";
                        }

                        leaf priority-decrement {
                            type uint8 {
                                range "1..254";
                            }
                            mandatory true;
                            description "There is no default, because a default
                                         picks the operator's failover policy. RFC
                                         9568 Section 8.3.2 says how far apart two
                                         routers' priorities belong.";
                            ze:help "Priority subtracted from this group while this interface is down.";
                        }
                    }
                }
            }
        }
    }

    grouping vrrp-group-ipv6 {
        description "VRRP groups on an IPv6 interface unit (RFC 9568 only).";

        container vrrp {
            ze:backend "netlink";
            description "Ze runs each group as its own state machine, on a macvlan
                         device that carries the group's virtual MAC. The device name
                         starts with zv6 and takes the parent ifindex and the VRID,
                         inside the 15-character kernel limit. Every group here is
                         VRRPv3, because VRRPv2 is IPv4 only, so this tree carries no
                         version leaf. The container carries ze:backend netlink, so a
                         tree with interface backend vpp is refused at verify with
                         \"VRRP requires the netlink interface backend\".";
            ze:help "VRRP virtual routers hosted on this IPv6 unit.";

            list group {
                key "name";
                description "The name is a config label only, and Ze never sends it on
                             the wire. The VRID leaf carries the protocol identity.";
                ze:help "One virtual router, identified by an operator-assigned name.";

                leaf name {
                    type zt:node-name;
                    description "Ze keys the running instance on interface, unit, family
                                 and this name. So a change to vrid reconfigures the
                                 same virtual router, and a change to the name removes
                                 one virtual router and creates another. The name is 1
                                 to 255 characters of letters, digits, underscore,
                                 hyphen and dot. The first character MUST be a letter, a
                                 digit or an underscore. Every VRRP error message opens
                                 with the name, because the operator typed it.";
                    ze:help "Config-level group name (free-form label, used as list key).
                             Not sent on the wire.";
                }

                leaf vrid {
                    type uint8 {
                        range "1..255";
                    }
                    mandatory true;
                    description "The VRID is unique per interface unit and per address
                                 family. The IPv4 VRID space and the IPv6 VRID space
                                 are independent.";
                    ze:help "Virtual Router Identifier (RFC 9568 Section 5.2.3).";
                }

                leaf-list virtual-address {
                    type zt:ipv6-address;
                    min-elements 1;
                    max-elements 16;
                    ze:syntax "bracket";
                    description "The FIRST address MUST be an IPv6 link-local address
                                 in fe80::/10, because it is the advertisement source
                                 identity (RFC 9568 Section 5.2.9, erratum 8300). The
                                 plugin verifier enforces it.";
                    ze:help "Virtual IPv6 addresses, encoded on the wire in configuration order.";
                }

                leaf priority {
                    type uint8 {
                        range "1..254";
                    }
                    default 100;
                    description "255 is reserved for the address owner, and Ze assigns
                                 it automatically.";
                    ze:help "Election priority (RFC 9568 Section 5.2.4).";
                }

                leaf preempt {
                    type boolean;
                    default "true";
                    description "The state machine reads this leaf in the Backup state
                                 only. With true, Ze discards an advertisement whose
                                 priority is lower than its own, so the Master_Down
                                 timer runs out and promotes this router. With false,
                                 Ze accepts that advertisement and re-arms the timer,
                                 so this router stays Backup while the Active router
                                 still sends. The default is true, and
                                 preempt-delay-seconds delays the takeover after the
                                 first losing advertisement.";
                    ze:help "Preempt_Mode (RFC 9568 Section 6.4.2).";
                }

                leaf preempt-delay-seconds {
                    type uint16 {
                        range "0..3600";
                    }
                    default 0;
                    description "RFC 9568 does not define this hold-time. Ze takes the
                                 behavior from Junos.";
                    ze:help "Preemption hold-time, in Junos semantics.";
                }

                leaf advertise-interval-milliseconds {
                    type uint32 {
                        range "10..40950";
                    }
                    default 1000;
                    description "The value is a multiple of 10 ms. The wire carries
                                 centiseconds (RFC 9568 erratum 8301).";
                    ze:help "Advertisement interval in milliseconds.";

                }

                leaf accept-mode {
                    type boolean;
                    default "false";
                    description "A non-owner Active router accepts packets addressed to
                                 the virtual addresses. Ze enforces the leaf in the
                                 dataplane, with an nftables input chain in the ze_vrrp
                                 table. With false, the chain accepts ICMPv6 types 135
                                 and 136 before it examines any address (RFC 9568
                                 Section 6.1). Neighbor Discovery for the virtual
                                 addresses still answers. The chain drops local delivery
                                 of every other packet to a virtual address, and leaves
                                 forwarding for the virtual MAC untouched. The address
                                 owner accepts whatever this leaf says.";
                    ze:help "Accept_Mode (RFC 9568 Section 6.1/6.4.3), v3 semantics.";
                }

                container track {
                    description "Ze sums the priority-decrement of every tracked
                                 interface that is down, and subtracts the sum from
                                 the configured priority. The result never falls
                                 below 1 (RFC 9568 Section 5.2.4), and Ze advertises
                                 the new priority at once. Tracking is refused on the
                                 group that owns its virtual address, because that
                                 group advertises 255 whatever a decrement says.";
                    ze:help "Interfaces whose loss lowers the priority this group advertises.";

                    list interface {
                        key "name";
                        max-elements 16;
                        description "Ze reads the interface's operational state only,
                                     so this interface does not need an address of
                                     the group's family. Two interfaces that are down
                                     cost the sum of their decrements.";
                        ze:help "One tracked interface and the priority its loss costs.";

                        leaf name {
                            type zt:node-name;
                            ze:validate "vrrp-track-interface";
                            description "Ze resolves the name through the resolver
                                         show interface uses, so a kernel device the
                                         interface tree does not carry still
                                         resolves. A name that resolves to no device
                                         counts as DOWN, and Ze logs the resolver
                                         error at warn.";
                            ze:help "Interface to watch, by interface-tree name or kernel device name.";
                        }

                        leaf priority-decrement {
                            type uint8 {
                                range "1..254";
                            }
                            mandatory true;
                            description "There is no default, because a default
                                         picks the operator's failover policy. RFC
                                         9568 Section 8.3.2 says how far apart two
                                         routers' priorities belong.";
                            ze:help "Priority subtracted from this group while this interface is down.";
                        }
                    }
                }
            }
        }
    }

    augment "/iface:interface/iface:ethernet/iface:unit/iface:ipv4" {
        uses vrrp-group-ipv4;
    }

    augment "/iface:interface/iface:ethernet/iface:unit/iface:ipv6" {
        uses vrrp-group-ipv6;
    }

    augment "/iface:interface/iface:veth/iface:unit/iface:ipv4" {
        uses vrrp-group-ipv4;
    }

    augment "/iface:interface/iface:veth/iface:unit/iface:ipv6" {
        uses vrrp-group-ipv6;
    }

    augment "/iface:interface/iface:bridge/iface:unit/iface:ipv4" {
        uses vrrp-group-ipv4;
    }

    augment "/iface:interface/iface:bridge/iface:unit/iface:ipv6" {
        uses vrrp-group-ipv6;
    }

    augment "/iface:interface/iface:dummy/iface:unit/iface:ipv4" {
        uses vrrp-group-ipv4;
    }

    augment "/iface:interface/iface:dummy/iface:unit/iface:ipv6" {
        uses vrrp-group-ipv6;
    }
}
