module ze-flowexport-conf {
    namespace "urn:ze:flowexport:conf";
    prefix flowexport;

    import ze-types { prefix zt; }
    import ze-extensions { prefix ze; }

    container flow-export {
        description "Flow export configuration. Ze exports interface counters to every collector. It exports per-flow
                     records as well when the conntrack container or the sampling container is enabled. Each collector
                     names its own protocol, so one device can feed an sFlow collector and an IPFIX collector at the
                     same time.";
        ze:help "Flow export (sFlow, NetFlow v9, IPFIX) configuration";

        list collector {
            key "name";
            description "A flow export collector endpoint. Ze opens one UDP sender for each entry and encodes for the
                protocol that entry names. address and protocol are both mandatory, so a commit that leaves either
                one out is rejected. max-datagram-size bounds each UDP payload, including padding.";
            ze:help "A flow export collector endpoint";

            leaf name {
                type string;
                description "Collector name, and the key of this list. The name labels this collector in the export
                    metrics and in the log lines that report a send failure. It reaches no datagram.";
                ze:help "Collector name";
            }

            leaf address {
                type zt:ip-address;
                mandatory true;
                description "Collector IP address, and the leaf is mandatory. The address and port together are where Ze
                    sends every datagram of this collector. A commit that gives a value Ze cannot parse as an
                    address is rejected.";
                ze:help "Collector IP address";
            }

            leaf port {
                type uint16 {
                    range "1..65535";
                }
                default 6343;
                description "Collector UDP port. The default 6343 is the port sFlow collectors listen on, so a NetFlow v9
                    or an IPFIX collector usually needs its own port written here. The port is per collector, so two
                    entries can send to one address on two ports.";
                ze:help "Collector UDP port";
            }

            leaf source-address {
                type zt:ip-address;
                description "Source IP address for outbound flow export datagrams. Ze binds the UDP socket of this
                    collector to the address. Left out, the kernel selects a source from its route to the collector.
                    The value does not reach the sFlow datagram header, which carries agent-address instead.";
                ze:help "Source IP address for outbound flow export datagrams";
            }

            leaf max-datagram-size {
                type uint16 {
                    range "464..1400";
                }
                default 464;
                description "Largest UDP payload Ze sends to this collector, in octets. Encoders include padding
                    within this bound. RFC 7011 Section 10.3.3 recommends packets of at most 512 octets when the
                    path MTU is unknown. The default 464 reserves 48 octets for IPv6 and UDP headers.
                    Set a larger value only for a known path MTU, after subtracting all IP, UDP and tunnel headers.
                    The ceiling 1400 is the encoding buffer size.";
                ze:help "Largest UDP payload sent to this collector, in octets";
            }

            leaf protocol {
                type enumeration {
                    enum sflow {
                        ze:help "sFlow v5";
                    }
                    enum netflow9 {
                        ze:help "NetFlow v9 (RFC 3954)";
                    }
                    enum ipfix {
                        ze:help "IPFIX (RFC 7011)";
                    }
                }
                mandatory true;
                description "Export protocol, and the leaf is mandatory. The value selects the encoder Ze builds for this
                    collector. It also decides which of the other leaves are read. sub-agent-id and agent-address
                    are read by sflow alone, and observation-domain by netflow9 and ipfix alone.";
                ze:help "Export protocol";
            }

            leaf polling-interval {
                type uint16 {
                    range "1..3600";
                }
                default 20;
                description "Counter polling interval in seconds, 1 to 3600, default 20. The interval is a maximum: Ze sends the
                    interface counters to this collector at least once in each interval. Counter snapshots arrive once
                    a second, so Ze polls from one second before the interval ends. The counter snapshot is shared
                    between collectors, so a short interval on one collector does not make another one faster.";
                ze:help "Counter polling interval in seconds";
            }

            leaf template-refresh {
                type uint32 {
                    range "1..86400";
                }
                default 600;
                description "Template refresh interval in seconds, 1 to 86400, default 600. NetFlow v9 and IPFIX resend the
                    record template on this interval, so a collector that restarts can decode the records again. The
                    counter template and the flow template each keep their own timer. The sFlow encoder has no
                    template and does nothing with the value.";
                ze:help "Template refresh interval in seconds (NetFlow v9, IPFIX)";
            }

            leaf sub-agent-id {
                type uint32;
                default 0;
                description "sFlow sub-agent identifier, default 0. Ze writes it into the sFlow v5 datagram header. It
                    separates several sFlow agents that share one agent-address, so a collector can keep their
                    sequence numbers apart. Every sflow collector exports every interface, and sFlow v5 binds each
                    data source to one sub-agent, so all sflow collectors must name the same value: the config is
                    refused otherwise. A netflow9 or ipfix collector does not read the leaf.";
                ze:help "sFlow sub-agent identifier";
            }

            leaf observation-domain {
                type uint32;
                default 0;
                description "IPFIX and NetFlow v9 observation domain ID, default 0. Ze writes it into the message header of
                    every counter message and every flow message of those two protocols. A collector uses it to keep
                    the record streams of one exporter apart. An sflow collector does not read the leaf.";
                ze:help "IPFIX/NetFlow v9 observation domain ID";
            }

            leaf agent-address {
                type zt:ip-address;
                description "sFlow agent address, which is the device's own stable IP address. Ze writes it into the sFlow
                    v5 datagram header, so a collector identifies the exporter by one address whichever interface
                    the datagram left. It is mandatory on an sflow collector, 0.0.0.0 and :: are refused, and all
                    sflow collectors must name the same address, because Ze is one sFlow agent. Two spellings
                    of one address, such as 2001:db8::1 and 2001:DB8:0::1, are the same address. A netflow9 or ipfix
                    collector does not read the leaf.";
                ze:help "sFlow agent address (device's own stable IP, e.g. loopback)";
            }
        }

        container sampling {
            description "Packet sampling exported as sFlow flow samples. Ze installs a tc sample action on each listed
                    interface and reads the sampled headers from the kernel psample netlink family. The path is
                    Linux only. A setup failure is logged and leaves that interface unsampled, and the rest of the
                    exporter keeps running.";
            ze:help "Packet sampling (tc sample + psample) exported as sFlow flow samples";

            list interface {
                key "name";
                description "Per-interface packet sampling configuration. Ze installs the tc action for each entry on its
                    own, so a failure on one entry does not stop another. Ze maps each sample the kernel delivers
                    back to its entry by kernel interface index.";
                ze:help "Per-interface packet sampling configuration";

                leaf name {
                    type string;
                    description "Interface to sample, and the key of this list. Ze installs the tc sample action on this
                        interface and resolves its kernel index once, so a sample is reported under this name.";
                    ze:help "Interface to sample";
                }

                leaf rate {
                    type uint32 {
                        range "1..1000000";
                    }
                    description "Sampling rate, as one packet in N. The leaf has no default, so an entry that leaves it out
                        fails the commit with 'rate 0 out of range 1-1000000'. Ze passes the value to the tc sample
                        action, and the kernel does the sampling.";
                    ze:help "Sampling rate (1-in-N packets)";
                }

                leaf trunc-size {
                    type uint16 {
                        range "64..1500";
                    }
                    default 128;
                    description "Bytes of each sampled packet header to capture, 64 to 1500, default 128. The tc sample
                        action truncates the frame to this length before the kernel passes it up. A larger value
                        carries more of the packet into the sFlow flow sample, and it costs more bandwidth toward
                        the collector.";
                    ze:help "Bytes of each sampled packet header to capture";
                }

                leaf group {
                    type uint32 {
                        range "1..2147483647";
                    }
                    default 1;
                    description "psample group ID, default 1. Ze writes it into the tc sample action, which tags each
                        sample the kernel emits. Ze does not read it back. The reader joins the psample packets
                        multicast group and maps each sample to its interface by index. This value therefore does
                        not select which samples Ze reads.";
                    ze:help "psample group ID";
                }
            }
        }

        container conntrack {
            description "Per-flow record export from conntrack. Ze dumps the kernel conntrack table on a timer and turns
                    each live entry into a flow record for the NetFlow v9 and IPFIX collectors. The same records
                    fill the recent-flow ring that 'show flow recent' and the DDoS characterization read.";
            ze:help "Per-flow record export from conntrack (NetFlow v9, IPFIX)";

            leaf enabled {
                type boolean;
                default false;
                description "Export per-flow records from the conntrack table. Left false, Ze starts no conntrack worker and
                    allocates no recent-flow ring. 'show flow recent' then has nothing to read, and the DDoS
                    characterization loses its flow input and falls back to its coarse target.";
                ze:help "Export per-flow records from the conntrack table";
            }

            leaf active-timeout {
                type uint16 {
                    range "1..3600";
                }
                default 60;
                description "Seconds between conntrack table dumps, 1 to 3600, default 60. Each dump turns the live
                    conntrack entries into flow records. Ze also drops its own tracking state for a flow it has not
                    seen for twice this time. A short timeout therefore shortens that memory too.";
                ze:help "Seconds between conntrack table dumps";
            }

            leaf recent-flow-ring {
                type uint32 {
                    range "64..65536";
                }
                default 4096;
                description "`show flow recent` reads the ring, and the ring feeds the on-box DDoS characterization. A larger
                    value keeps more history and uses more memory. Ze allocates the ring only when conntrack export is
                    enabled.";
                ze:help "Capacity of the recent-flow ring, in flow records.";
            }
        }

        container enrichment {
            description "Flow record enrichment from the BGP RIB. Ze keeps a prefix-to-AS radix tree that BGP best-path
                    changes feed. A flow record reads its next hop and its AS numbers from that tree. The tree is
                    swapped whole, so a record never reads a half-built tree.";
            ze:help "Flow record enrichment from the BGP RIB";

            leaf bgp {
                type boolean;
                default false;
                description "Enrich flow records with the BGP next hop, and with the AS numbers where the RIB carries them.
                    Ze subscribes to the RIB best-path changes and rebuilds the lookup tree at most once per rebuild
                    interval. A full-table replay event carries no AS_PATH, so those entries hold no AS until the
                    next incremental change corrects them.";
                ze:help "Enrich flow records with BGP next-hop (and AS where available)";
            }
        }
    }
}
