module ze-exabgp-bridge-conf {
    namespace "urn:ze:exabgp-bridge:conf";
    prefix exabgp-bridge;

    import ze-types { prefix zt; }
    import ze-extensions { prefix ze; }

    description
        "In-process ExaBGP compatibility bridge configuration for Ze. The
         bridge runs as an internal plugin (plugin { internal exabgp-bridge })
         and spawns every ExaBGP-format script the process list declares as a
         subprocess, translating between ze JSON events and the external
         JSON/text command formats. The equivalent external form is
         `ze exabgp plugin <cmd>` launched by the process manager, which carries
         one script; internal mode is additive and needs the script commands
         delivered through this config root rather than the process-manager
         `run` line.

         The settings nest under a top-level `exabgp` container so that root
         stays available for future exabgp-related configuration; the bridge
         itself lives in the `bridge` child container (user directive
         2026-07-09). The registry plugin name remains exabgp-bridge.";

    revision 2026-09-06 {
        description
            "Replace the single run leaf with a process list. An ExaBGP config
             declares any number of process blocks, and the bridge ran one of
             them. Add the encoder leaf, which ExaBGP declares per process, and
             the feed list, which carries the neighbors that name this process
             in their api block and the events each one grants it.";
    }

    revision 2026-07-09 {
        description "Initial revision (spec-followup-subsystem AC-1).";
    }

    container exabgp {
        description
            "The bridge itself lives in the bridge container under this root, which
             keeps the root free for other ExaBGP compatibility settings. The plugin is
             registered as exabgp-bridge, so plugin { internal exabgp-bridge } starts
             it. The bridge refuses to start until bridge run names a script.";
        ze:help "Top-level container for ExaBGP-compatibility configuration.";

        container bridge {
            description "Present this container to configure the internal exabgp-bridge
plugin.";
            ze:help "In-process ExaBGP bridge settings.";

            list process {
                key "name";
                description "One block per script. An ExaBGP configuration declares the same set as
'process <name> { run ... }', and the migration writes one block here for each of them. Ze
starts every block, sends every event to every script, and reads commands from every script.
The bridge does nothing until one block names a run command.";
                ze:help "One ExaBGP-format script the bridge runs as a subprocess.";

                leaf name {
                    type string {
                        length "1..64";
                    }
                    description "The key of the block. Ze puts the name in its log lines, and an
ExaBGP neighbor's 'api { processes [ ... ] }' list refers to a script by this name. Keep the
name the ExaBGP configuration used.";
                    ze:help "Name of the script, as the ExaBGP process block spelled it.";
                }

                leaf run {
                    type string {
                        length "1..4096";
                    }
                    description "Two examples are './plugin.py' and 'python3 /opt/plugin.py'. Ze
splits the line into words as a POSIX shell does, with no expansion: blanks separate
words, and single or double quotes group them, so a quoted argument holding a space
reaches the script as one argument. The first word is the executable, and the rest are
its arguments. A block with no run command, or with an unclosed quote, is refused.";
                    ze:help "Command line of the script.";
                }

                leaf encoder {
                    type enumeration {
                        enum text { ze:help "Write each event as one line in the ExaBGP text format."; }
                        enum json { ze:help "Write each event as one JSON object."; }
                    }
                    default text;
                    description "json writes one JSON object per event. text writes ExaBGP's
one-event-per-line format, such as 'neighbor 127.0.0.1 receive update announced 10.0.0.0/24
next-hop 10.0.0.1 origin igp'. ExaBGP spells this leaf the same way and declares it per process,
so one bridge can feed a text script and a JSON script at once. The default is text, as ExaBGP's.
The leaf is read with the script's API version, as ExaBGP 6.0 reads it: a script that writes
'peer ...' reads 6.0.0 JSON whatever this says, a script that writes 'announce ...' or
'neighbor ...' reads 5.x text or 5.x JSON (envelope 4.0.1), and a script that has written
neither yet reads 5.x text when this is text and 6.0.0 JSON when it is json.";
                    ze:help "Format the script's events are written in.";
                }

                list feed {
                    key "peer";
                    description "An ExaBGP neighbor names the processes it feeds in
'api { processes [ ... ] }' and the message kinds it feeds them in the same block, so the
relation is per peer AND per script. The migration writes one block here for each neighbor that
named this script. Ze also sends a command that names no neighbor to these peers alone. A
process with NO feed block is fed by every peer with every event, which is what one script and
one neighbor means.";
                    ze:help "One peer that feeds this script, and the events it feeds.";

                    leaf peer {
                        type zt:ip-address;
                        description "The address the peer's own 'connection { remote { ip ... } }' declares.";
                        ze:help "Address of the peer that feeds this script.";
                    }

                    leaf-list event {
                        type string;
                        ze:syntax "bracket";
                        description "ExaBGP's own event names: 'receive-update', 'send-update',
'receive-open', 'send-keepalive', 'receive-notification', 'send-refresh', 'receive-operational'
and their siblings, plus 'neighbor-changes', 'negotiated', 'fsm' and 'signal', and the forms a
direction's messages are written in: 'receive-packets', 'receive-consolidate', 'receive-parsed'
and their 'send-' siblings, as ExaBGP's 'packets', 'consolidate' and 'parsed'. An EMPTY list
feeds no event from this peer, which is what an ExaBGP api block that names a process and no
message kind does.";
                        ze:help "Events this peer feeds this script.";
                    }
                }

                leaf respawn {
                    type boolean;
                    default true;
                    description "true starts the script again the moment it exits. false leaves it
stopped, which is what a script that does its work once and exits needs. A script that exits
more than five times in 64 seconds stays stopped whatever this leaf holds, and Ze logs that it
did. ExaBGP spells this leaf the same way and applies the same limit.";
                    ze:help "Start the script again when it exits.";
                }

                leaf on-exit {
                    type enumeration {
                        enum keep { ze:help "Leave the routes the script announced in place."; }
                        enum withdraw { ze:help "Withdraw the routes the script announced."; }
                    }
                    description "What becomes of the routes this script announced when it exits.
keep leaves them; withdraw withdraws every route the script was the last to announce, before
a restarted script writes its first line. Left unset, a script that writes the ExaBGP 4 API
('announce ...', 'neighbor ...') keeps its routes, as ExaBGP 4.x and 5.x did, and any other
has them withdrawn, as ExaBGP 6.0 does. Each exit is logged with the choice and its reason.
ExaBGP spells this leaf the same way.";
                    ze:help "Keep or withdraw the script's routes when it exits.";
                }
            }

            leaf-list family {
                type zt:address-family;
                description "One example is ipv4/unicast. If this leaf-list is empty, the
bridge negotiates ipv4/unicast.";
                ze:help "Address families the bridge negotiates for the script.";
            }

            leaf route-refresh {
                type boolean;
                default false;
                description "RFC 2918 defines the route-refresh capability. When this leaf is
true, Ze advertises the capability on every session the bridge feeds.";
                ze:help "Advertise the BGP route-refresh capability.";
            }

            leaf add-path {
                type enumeration {
                    enum none { ze:help "Advertise no ADD-PATH capability."; }
                    enum receive { ze:help "Send/Receive value 1: accept more than one path from the peer."; }
                    enum send { ze:help "Send/Receive value 2: advertise more than one path to the peer."; }
                    enum both { ze:help "Send/Receive value 3: accept and advertise more than one path."; }
                }
                default none;
                description "RFC 7911 defines ADD-PATH. none disables it. receive accepts more
than one path from the peer. send advertises more than one path to the peer. both does
each of the two.";
                ze:help "ADD-PATH mode for the families the bridge negotiates.";
            }
        }
    }
}
