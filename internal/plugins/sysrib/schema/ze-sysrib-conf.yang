module ze-sysrib-conf {
    namespace "urn:ze:sysrib:conf";
    prefix sysrib;

    description
        "System RIB configuration for Ze.
         Admin distance settings control cross-protocol route selection.
         Lower distance wins. Used by the sysrib plugin to override
         incoming priority values from protocol RIBs.";

    revision 2026-04-04 {
        description "Add admin-distance container.";
    }

    container sysrib {
        description "System RIB configuration.";

        container admin-distance {
            description
                "Administrative distance per protocol.
                 Lower value wins. Used by the system RIB to select
                 the best route across protocols.";

            leaf connected {
                type uint8;
                default 0;
                description "Directly connected networks.";
            }

            leaf static {
                type uint8;
                default 10;
                description "Static routes.";
            }

            leaf ebgp {
                type uint8;
                default 20;
                description "External BGP routes.";
            }

            leaf ospf {
                type uint8;
                default 110;
                description "OSPF routes.";
            }

            leaf isis {
                type uint8;
                default 115;
                description "IS-IS routes.";
            }

            leaf ibgp {
                type uint8;
                default 200;
                description "Internal BGP routes.";
            }
        }
    }
}
