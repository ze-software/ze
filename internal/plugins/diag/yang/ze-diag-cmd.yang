module ze-diag-cmd {
    namespace "urn:ze:diag:cmd";
    prefix diagcmd;
    import ze-extensions { prefix ze; }
    description "Diagnostic command tree: capture (control-plane, raw, interface), tcp-check, and request wireguard keypair. Owned by the diag component. See ai/rules/plugin-self-containment.md.";
    revision 2026-11-14 { description "request wireguard keypair makes the keys in process; the wg binary is no longer needed."; }
    revision 2026-10-12 { description "Rename generate wireguard keypair to request wireguard keypair: the first word of a command is its verb."; }
    revision 2026-10-08 { description "Declare generate wireguard keypair, which the diag plugin already served."; }
    revision 2026-06-06 { description "Relocated capture and tcp-check out of the central show schema (plugin self-containment)."; }

    container show {
        config false;
        ze:help "Read-only commands to inspect system, protocol, and network state.";

        container tcp-check {
            config false;
            ze:command "ze-diag:show-tcp-check";
            description "Tries to open a TCP connection and reports success or failure with the
connection time. Use 'source <IP>' to bind a specific local address. Quick way
to verify a peer's BGP port is reachable.";
            ze:help "Test TCP connectivity to a remote host and port.";
            leaf host {
                type string;
                mandatory true;
                description "An IP address or a DNS name of at most 253 characters, which the dialer
resolves. The answer echoes it in the host key.";
                ze:help "Target host.";
            }
            leaf port {
                type uint16;
                mandatory true;
                description "The TCP port to connect to, from 1 to 65535. Ze joins it to the host and
dials that one endpoint.";
                ze:help "Target port.";
            }
            leaf source {
                type string;
                description "A local IP address the connection binds to before it dials. An address
the host does not hold makes the dial fail. Absent, the kernel picks the source.";
                ze:help "Source IP address.";
            }
            leaf timeout {
                type string {
                    pattern '\d+[smh]?';
                }
                description "How long the dial waits before it reports timeout, from 1s to 30s. The
default is 5s.";
                ze:help "Connection timeout.";
            }
        }

        container capture {
            config false;
            ze:command "ze-diag:show-capture";
            ze:rpc "ze-cli-show-api:capture";
            description "Returns protocol messages you previously enabled capture for. Without a
protocol keyword, shows all protocols. Use this to debug session establishment
issues.";
            ze:help "Show captured control-plane messages.";
            leaf protocol {
                type enumeration {
                    enum l2tp { ze:help "Show only the L2TP control messages."; }
                    enum bgp { ze:help "Show only the BGP messages."; }
                }
                description "Restricts the answer to one protocol key. Absent, the answer carries an
l2tp key and a bgp key, each holding its messages or 'capture not enabled'.";
                ze:help "Protocol filter.";
            }
            leaf tunnel-id {
                // Identifiers are string-typed (ai/rules/cli-grammar.md "Identifiers
                // Are Strings"); the pattern keeps the 0-65535 numeric shape.
                type string {
                    pattern '[0-9]{1,5}';
                }
                description "Keeps only the L2TP messages of the tunnel with this local tunnel ID. The
BGP messages are not affected.";
                ze:help "L2TP tunnel ID filter.";
            }
            leaf count {
                type uint32;
                description "At most this many messages are returned for each protocol. Absent or 0,
every buffered message is returned.";
                ze:help "Maximum number of messages.";
            }
            leaf peer {
                type string;
                description "Keeps only the messages exchanged with this peer address, for L2TP and BGP
alike.";
                ze:help "Peer address filter.";
            }

            container raw {
                config false;
                ze:command "ze-diag:show-capture-raw";
                description "Actions: start (begin capturing), stop (halt), dump (retrieve). Protocols:
l2tp, bgp. Output formats: pcap (for Wireshark), json. Limit with count <N>.";
                ze:help "Control raw byte capture for protocol debugging.";
                leaf action {
                    type enumeration {
                        enum start { ze:help "Turn raw capture on and answer with the protocols it started for."; }
                        enum stop { ze:help "Turn raw capture off and answer with the protocols it stopped for."; }
                        enum dump { ze:help "Return the captured bytes in the chosen format without changing the capture state."; }
                    }
                    description "The verb the command performs. It is required, and a call without one is
refused with the usage line.";
                    ze:help "Capture action.";
                }
                leaf protocol {
                    type enumeration {
                        enum l2tp { ze:help "Apply the action to the L2TP capture alone."; }
                        enum bgp { ze:help "Apply the action to the BGP capture alone."; }
                    }
                    description "Narrows the action to one protocol. Absent, the action applies to every
protocol with a raw capture, and the answer carries one key for each.";
                    ze:help "Protocol to capture.";
                }
                leaf format {
                    type enumeration {
                        enum pcap { ze:help "Return the bytes as a base64 pcap file, ready for Wireshark."; }
                        enum json { ze:help "Return one row per message with its timestamp, direction and byte count."; }
                    }
                    description "Read by dump alone. The default is json. With pcap the answer carries a
<protocol>-pcap key holding the base64 file and a <protocol>-packets count.";
                    ze:help "Output format.";
                }
                leaf count {
                    type uint32;
                    description "Read by dump alone. At most this many messages are returned for each
protocol. Absent or 0, every captured message is returned.";
                    ze:help "Maximum number of messages.";
                }
            }

            container interface {
                config false;
                ze:command "ze-diag:show-capture-interface";
                description "Uses AF_PACKET for zero-copy capture. Filter by protocol and port. Limit with
count or duration. Output as pcap (for Wireshark) or text. Snap-len controls
how many bytes per packet are captured.";
                ze:help "Capture live packets on an interface (like tcpdump).";
                leaf iface {
                    type string;
                    description "The interface name as the configuration spells it. Ze resolves it to the
kernel device before it opens the socket. One capture at a time runs per interface, and a
second call on the same name is refused.";
                    ze:help "Interface name.";
                }
                leaf count {
                    type uint32 {
                        range "1..10000";
                    }
                    description "The capture ends when this many packets have been read or when the
duration has elapsed, whichever comes first. The default is 100.";
                    ze:help "Packet count.";
                }
                leaf duration {
                    type string {
                        pattern '\d+[smh]?';
                    }
                    description "The time the socket stays open, from 1s to 60s. The default is 10s. The
capture ends earlier when the packet count is reached.";
                    ze:help "Capture duration.";
                }
                leaf snap-len {
                    type uint32 {
                        range "64..65535";
                    }
                    description "The number of bytes kept from the start of each packet. The default is
65535, which keeps whole packets. The value is written into the pcap file header.";
                    ze:help "Snap length in bytes.";
                }
                leaf format {
                    type enumeration {
                        enum pcap { ze:help "Return the packets as a base64 pcap file, ready for Wireshark."; }
                        enum text { ze:help "Return one decoded line per packet, in the style of tcpdump."; }
                    }
                    description "The default is pcap. Both forms carry a packets count with the data.";
                    ze:help "Output format.";
                }
                leaf protocol {
                    type string;
                    description "A pcap-filter word such as tcp or udp. Ze joins it to every other word
after the interface name and compiles the whole expression to a BPF program on the
socket.";
                    ze:help "Protocol filter.";
                }
            }
        }
    }

    container request {
        config false;

        container wireguard {
            config false;
            description "WireGuard material, made by Ze itself.";
            ze:help "Request WireGuard material.";

            container keypair {
                config false;
                ze:command "ze-diag:request-wireguard-keypair";
                description "The private key is written on the first line and the public key on the
second. Ze makes the keys itself, so no other program is needed.";
                ze:help "Generate a WireGuard keypair.";
            }
        }
    }
}
