module ze-gnmi-cmd {
    namespace "urn:ze:gnmi:cmd";
    prefix gnmicmd;
    import ze-extensions    { prefix ze; }
    import ze-cli-show-cmd  { prefix clishowcmd; }
    // Relocated from the central show schema, for plugin self-containment.
    description "gNMI show command: server status and configuration.";
    revision 2026-06-03 { description "Initial revision: relocated from ze-cli-show-cmd."; }

    augment "/clishowcmd:show" {
        container gnmi {
            config false;
            ze:command "ze-gnmi:show-gnmi";
            description "Returns listen address, TLS details, authentication mode, and the number of
active streaming subscribers.";
            ze:help "Show whether the gNMI server is running and how it is configured.";
        }
    }
}
