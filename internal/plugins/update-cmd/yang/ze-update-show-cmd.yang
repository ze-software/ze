module ze-update-show-cmd {
    namespace "urn:ze:update:show:cmd";
    prefix updateshowcmd;
    import ze-extensions { prefix ze; }
    description "show system update command tree. Owned by the update component because these handlers read the firmware update backend status. See ai/rules/plugin-self-containment.md.";
    revision 2026-06-06 { description "Relocated show system update out of the central show schema (plugin self-containment)."; }

    container show {
        config false;
        ze:help "Read-only commands to inspect system, protocol, and network state.";

        container system {
            config false;
            ze:help "Daemon process and runtime diagnostics.";

            container update {
                config false;
                ze:command "ze-update:show-system-update";
                ze:rpc "ze-update-api:system-update";
                description "Shows the running version, latest available version, and when the last check
ran. Use 'update system firmware check' to trigger an immediate re-check.";
                ze:help "Check if a firmware update is available.";

                container history {
                    config false;
                    ze:command "ze-update:show-system-update-history";
                    ze:rpc "ze-update-api:system-update-history";
                    description "Lists the last 20 update events: checks, downloads, installs, and rollbacks
with timestamps and outcomes.";
                    ze:help "Show recent firmware update activity.";
                }
            }
        }
    }
}
