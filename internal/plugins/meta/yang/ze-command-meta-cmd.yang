module ze-command-meta-cmd {
    namespace "urn:ze:command:meta:cmd";
    prefix commandmetacmd;
    import ze-extensions { prefix ze; }
    description "Command discovery, help, completion, event listing, and plugin session configuration. Owned by the command component because these handlers read the cross-plugin command registry and event registry through the command/pluginserver layer. See ai/rules/plugin-self-containment.md.";
    revision 2026-06-06 { description "Relocated help/command/event/plugin out of the central meta schema (plugin self-containment)."; }
    revision 2026-07-02 { description "Verb-first: event list -> show event list, command list/help/complete -> show command list/help/complete. plugin encoding/format/ack stay noun-first (plugin-session namespace; set plugin collides with the config-tree plugin node)."; }

    container help {
        config false;
        ze:command "ze-meta:bgp-help";
        ze:rpc "ze-bgp-api:help";
        description "Lists every registered command verb with a brief description.";
        ze:help "Show available commands at this level.";
    }

    container show {
        config false;
        ze:help "Read-only commands to inspect system, protocol, and network state.";

        container event {
            config false;
            // Description is owned by the central show schema's `event` container
            // (ze-cli-show-cmd.yang, which holds recent/namespaces). This module
            // only merges the `list` leaf onto it, so it does not redeclare the
            // description (a mismatch triggers a loader warning).

            container list {
                config false;
                ze:command "ze-meta:bgp-event-list";
                ze:rpc "ze-bgp-api:event-list";
                description "Shows event name, category, and payload structure. Use this to discover what
events are available before subscribing.";
                ze:help "List every event type you can subscribe to.";
            }
        }

        container command {
            config false;
            description "The answers are built from the registries this binary links. A command
                         absent here is one the build did not include, and not one an operator
                         misspelled.";
            ze:help "Command discovery and completion.";

            container list {
                config false;
                ze:command "ze-meta:bgp-command-list";
                ze:rpc "ze-bgp-api:command-list";
                description "Returns dispatch key and description for each. Useful for scripting or
discovering commands not shown in the top-level help.";
                ze:help "List every command the daemon knows about.";
            }

            container help {
                config false;
                ze:command "ze-meta:bgp-command-help";
                ze:rpc "ze-bgp-api:command-help";
                description "Gives you the full description, expected arguments, and usage pattern for one
command.";
                ze:help "Show usage and arguments for a specific command.";
            }

            container complete {
                config false;
                ze:command "ze-meta:bgp-command-complete";
                ze:rpc "ze-bgp-api:command-complete";
                description "Returns possible completions for the given input. Used internally by the CLI
editor, but also callable for scripting.";
                ze:help "Get tab-completion candidates for a partial command.";
            }
        }
    }

    container plugin {
        config false;
        description "The settings bind to the session that issues them, so another plugin session is
                     unaffected. They are lost when that session ends.";
        ze:help "Configure how events are delivered to your plugin session.";

        container encoding {
            config false;
            ze:command "ze-meta:bgp-plugin-encoding";
            ze:rpc "ze-bgp-api:plugin-encoding";
            description "Controls how events are serialized in this session. JSON is structured and
parseable; text is more compact.";
            ze:help "Choose json or text encoding for plugin events.";
        }

        container format {
            config false;
            ze:command "ze-meta:bgp-plugin-format";
            ze:rpc "ze-bgp-api:plugin-format";
            description "hex and base64 are compact wire representations. parsed decodes attributes
into structured fields. full includes both wire bytes and parsed content.";
            ze:help "Choose how BGP message bytes appear in events.";
        }

        container ack {
            config false;
            ze:command "ze-meta:bgp-plugin-ack";
            ze:rpc "ze-bgp-api:plugin-ack";
            description "sync: Ze waits for your plugin to acknowledge each event before sending the
next one. Safer but slower. async: events fire without waiting, giving higher
throughput at the cost of backpressure control.";
            ze:help "Choose sync or async event delivery.";
        }
    }
}
