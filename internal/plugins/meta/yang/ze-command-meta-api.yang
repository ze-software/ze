module ze-command-meta-api {
  namespace "urn:ze:command:meta:api";
  prefix command-meta-api;

  import ze-extensions { prefix ze; }

  organization "Ze Project";
  description
    "Command discovery, completion, and plugin configuration RPCs.
     Owned by the command component. See ai/rules/plugin-self-containment.md.";

  revision 2026-06-06 {
    description "Relocated from central meta API schema (plugin self-containment).";
  }

  rpc help {
    description "The same operation is spelled 'help' on the CLI. Each entry joins a builtin
command name to its summary with a hyphen. A plugin's own command sits in the
command registry instead, so command-help is the RPC that reaches it.";
    ze:help "List subcommands.";
  }

  rpc command-list {
    description "The same operation is spelled 'show command list' on the CLI. Each row carries the
command name and its one-line summary. Give the 'verbose' argument and each row
also carries its source, which is 'builtin'.";
    ze:help "List commands.";
  }

  rpc command-help {
    description "The same operation is spelled 'show command help' on the CLI. The answer carries
the one-line summary under 'short-help' and the long explanation under
'description'. Neither text is derived from the other.";
    ze:help "Show command details.";
  }

  rpc command-complete {
    description "The same operation is spelled 'show command complete' on the CLI, and the CLI
editor calls it for every keystroke. The match is a case-insensitive prefix over
the command names. A prefix that matches nothing answers an empty list and not
an error.";
    ze:help "Complete command/args.";
  }

  rpc event-list {
    description "The same operation is spelled 'show event list' on the CLI. Each entry carries the
event type name and its description. subscribe takes its event names from the
same registry.";
    ze:help "List available event types.";
  }

  rpc plugin-encoding {
    description "The same operation is spelled 'plugin encoding' on the CLI. 'json' is the default.
The daemon holds the mode on the calling process, so it changes nothing for
another plugin.";
    ze:help "Set event encoding (json|text).";
  }

  rpc plugin-format {
    description "The same operation is spelled 'plugin format' on the CLI. 'parsed' carries the
decoded fields alone and is the default. 'hex' and 'base64' carry the wire bytes
in that encoding. 'full' carries the decoded fields and the wire bytes
together.";
    ze:help "Set wire format (hex|base64|parsed|full).";
  }

  rpc plugin-ack {
    description "The same operation is spelled 'plugin ack' on the CLI. 'sync' makes the daemon wait
for wire transmission before it answers the ACK. 'async' answers as soon as the
command is accepted, and it is the default.";
    ze:help "Set ACK timing (sync|async).";
  }
}
