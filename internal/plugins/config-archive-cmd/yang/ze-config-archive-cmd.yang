module ze-config-archive-cmd {
    namespace "urn:ze:config:archive:cmd";
    prefix cfgarchivecmd;
    import ze-extensions { prefix ze; }
    description "Save configuration snapshots to the config store";
    revision 2026-05-17 { description "Initial revision"; }

    container request {
        config false;

        container config {
            config false;
            description "A snapshot records the configuration as it stands and does not apply anything.
                         Restoring one is a separate action.";
            ze:help "Configuration snapshot and archiving.";

            container archive {
                config false;
                ze:command "ze-config:archive-trigger";
                ze:rpc "ze-config-archive-api:trigger";
                description "Captures the config into the store for later rollback or comparison. Optional
name labels the snapshot; defaults to a timestamp.";
                ze:help "Save a snapshot of the current running configuration.";
            }
        }
    }
}
