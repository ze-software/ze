module ze-ospf-cmd {
    namespace "urn:ze:ospf:cmd";
    prefix ospfcmd;
    import ze-extensions { prefix ze; }
    description
        "show ospf ... command tree. Owned by the ospf component so removing it
         removes these command nodes together with the handlers in
         internal/plugins/ospf/cmd_show.go. The show subtree container-merges onto
         the generic show verb root; the wire methods bind into the CENTRAL ze-show
         namespace (Go-registered RPCs, the LDP/IS-IS model). Commands are
         object-rooted (no shared `ip` container); see
         docs/architecture/cli/command-namespacing.md and
         ai/rules/plugin-self-containment.md.";
    revision 2026-10-17 {
        description "clear ospf neighbor and clear ospf process alone are refused; clear ospf neighbor all
             tears down every adjacency, and clear ospf process all also re-runs SPF.";
    }
    revision 2026-07-02 {
        description "Add the `request ospf graceful-restart` operator action (RFC 3623 planned
             restart trigger, spec-ospf-ext-9); add `show ospf instance` for OSPFv2
             Multi-Instance (RFC 6549, spec-ospf-ext-12).";
    }
    revision 2026-06-26 {
        description "Object-rooted: dropped the show/clear `ip` container so the tree is show ospf ... / clear ospf ... (was show ip ospf ...).";
    }
    revision 2026-06-21 {
        description "Initial revision: show ip ospf neighbor/interface/database/route/border-routers/spf (spec-ospf-13).";
    }

    container show {
        config false;
        ze:help "Read-only commands to inspect system, protocol, and network state.";

        container ospf {
            config false;
            ze:command "ze-ospf:show-ospf";
            description "Returns the router-id, the areas, the ABR and ASBR status, and the
stub-router (max-metric) state.";
            ze:help "Show the OSPFv2 process summary (RFC 2328).";

            container instance {
                config false;
                ze:command "ze-ospf:show-instance";
                description "Lists each Instance ID with its router-id and the size of its isolated area,
interface, neighbor, and link-state database state.";
                ze:help "Show the configured OSPFv2 instances (RFC 6549 Multi-Instance).";
            }

            container graceful-restart {
                config false;
                ze:command "ze-ospf:show-graceful-restart";
                description "The restarter state (in-restart or not, grace end, reason) and the
per-neighbor helper sessions (which neighbors are being helped and their
remaining grace).";
                ze:help "Show OSPFv2 (IPv4) Graceful Restart state (RFC 3623).";
            }

            container segment-routing {
                config false;
                ze:command "ze-ospf:show-segment-routing";
                description "The configured SRGB/SRLB label ranges, the advertised SR-Algorithm,
this node's node Prefix-SIDs, and the Adjacency-SIDs allocated per adjacency.";
                ze:help "Show OSPFv2 (IPv4) Segment Routing state (RFC 8665).";
            }

            container ipv6 {
                config false;
                ze:command "ze-ospf:show-ipv6";
                description "Lists each configured address family (ipv6-unicast, ipv6-multicast,
ipv4-unicast, ipv4-multicast) with its Instance ID, router-id, and
neighbor/interface counts, so multiple AF instances on a link are
distinguishable.";
                ze:help "Show the OSPFv3 (IPv6) address-family instances (RFC 5838).";
                container interface {
                    config false;
                    ze:command "ze-ospf:show-ipv6-interface";
                    description "Returns per interface whether IPsec is configured, the protocol (ah/esp) and
SPI, and whether the kernel SA is installed. The key is never shown.";
                    ze:help "Show OSPFv3 (IPv6-family) interfaces and their RFC 4552 IPsec status.";
                    container detail {
                        config false;
                        ze:command "ze-ospf:show-ospfv3-interface-detail";
                        description "Returns the ISM state, the DR and BDR by Router ID, the timers, the
local Interface ID, and the Instance ID.";
                        ze:help "Show the full per-interface OSPFv3 state (spec-ospf-ext-14).";
                    }
                }
                container graceful-restart {
                    config false;
                    ze:command "ze-ospf:show-ipv6-graceful-restart";
                    description "The restarter state (in-restart or not, grace end, reason) and the
per-neighbor helper sessions (which neighbors are being helped and their
remaining grace).";
                    ze:help "Show OSPFv3 (IPv6) Graceful Restart state (RFC 5187).";
                }
                container segment-routing {
                    config false;
                    ze:command "ze-ospf:show-ipv6-segment-routing";
                    description "The configured SRGB/SRLB label ranges, the advertised SR-Algorithm,
this node's node Prefix-SIDs, and the Adjacency-SIDs allocated per adjacency.";
                    ze:help "Show OSPFv3 (IPv6) Segment Routing state (RFC 8666).";
                }
                container database {
                    config false;
                    ze:command "ze-ospf:show-ospfv3-database";
                    description "Base types decode into named fields; unknown function codes fall back to a
scope-aware header + body-hex view (spec-ospf-ext-14).";
                    ze:help "Show the OSPFv3 (IPv6) link-state database with each native scope-aware LSA decoded (RFC 5340).";
                    container detail {
                        config false;
                        ze:command "ze-ospf:show-ospfv3-database-detail";
                        description "The parent command decodes the base types only. This form decodes
every LSA body. An unknown function code then arrives as a scope-aware header
beside its body hex, rather than as a named record.";
                        ze:help "Decode every OSPFv3 LSA body with its scope-aware header (RFC 5340 section A.4.2.1).";
                    }
                    container router {
                        config false;
                        description "RFC 5340 Appendix A.4.3 gives the Router-LSA area flooding scope and the LS
Type 0x2001. Ze reads the per-area store for it. The bare form lists the
headers, and the detail form below decodes each body.";
                        ze:help "Router-LSAs (RFC 5340 section A.4.3).";
                        container detail {
                            config false;
                            ze:command "ze-ospf:show-ospfv3-database-router-detail";
                            description "Each body decodes into its interface records: the type, the metric, the
Interface ID, the neighbor Interface ID and the neighbor Router ID. RFC 5340
Section 2.2 states that a Router-LSA no longer contains a network address and
expresses topology only.";
                            ze:help "Decode each OSPFv3 Router-LSA body.";
                        }
                    }
                    container scope {
                        config false;
                        description "RFC 5340 Section 2.3 defines three flooding scopes, and the LS Type field
carries them in its S2 and S1 bits. Link-local scope stops at the link, area
scope stops at one area, and AS scope reaches the whole routing domain. The
three commands below read one scope each.";
                        ze:help "Filter the OSPFv3 database by RFC 5340 section A.4.2.1 flooding scope (S2/S1 bits).";
                        container link {
                            config false;
                            ze:command "ze-ospf:show-ospfv3-database-scope-link";
                            description "Ze reads the per-interface Link-LSA store as well as the area store, so a
Link-LSA appears here beside its interface. RFC 5340 Section 2.3 states that a
link-local LSA is flooded on the local link and no further.";
                            ze:help "Show only link-local (S2/S1 = 00) LSAs, including the per-interface Link-LSA store.";
                        }
                        container area {
                            config false;
                            ze:command "ze-ospf:show-ospfv3-database-scope-area";
                            description "RFC 5340 Section 2.3 gives area scope to the router-LSA, the network-LSA,
the inter-area-prefix-LSA, the inter-area-router-LSA and the
intra-area-prefix-LSA. Ze reads the per-area store for them.";
                            ze:help "Show only area-scope (S2/S1 = 01) LSAs.";
                        }
                        container as {
                            config false;
                            ze:command "ze-ospf:show-ospfv3-database-scope-as";
                            description "RFC 5340 Section 2.3 states that an AS-scope LSA is flooded throughout the
routing domain, and that a router which originates one is an AS Boundary
Router. Ze reads the AS-wide store for it, and no area appears in the answer.";
                            ze:help "Show only AS-scope (S2/S1 = 10) LSAs.";
                        }
                    }
                    container router-information {
                        config false;
                        ze:command "ze-ospf:show-ospfv3-database-router-information";
                        description "The LSA carries function code 12. Each one decodes into its
capability bits and its TLVs.";
                        ze:help "Show the OSPFv3 Router Information LSAs (RFC 7770).";
                    }
                    container extended {
                        config false;
                        ze:command "ze-ospf:show-ospfv3-database-extended";
                        description "Covers E-Router, E-Network, E-Inter-Area, E-AS-External, E-Link and
E-Intra-Area-Prefix. Each LSA decodes into named TLVs.";
                        ze:help "Show the extended OSPFv3 LSAs (RFC 8362).";
                    }
                    container segment-routing {
                        config false;
                        ze:command "ze-ospf:show-ospfv3-database-segment-routing";
                        description "This is a summary rather than a decode. The Segment Routing content lives in
the Router Information LSA and in the extended LSAs, and the two commands
above decode those LSAs in full.";
                        ze:help "Summarise the OSPFv3 Segment Routing content (RFC 8666) carried in the RI and extended LSAs.";
                    }
                }
                container instance {
                    config false;
                    ze:command "ze-ospf:show-ospfv3-instance";
                    description "Each instance carries its address family, its Instance ID, its area
count, and its neighbor count.";
                    ze:help "Enumerate the active OSPFv3 address-family instances (RFC 5838 section 2).";
                }
                container neighbor {
                    config false;
                    ze:command "ze-ospf:show-ospfv3-neighbor";
                    description "Each neighbor carries the link-local address as its identity, the
adjacency state, the DR and BDR by Router ID, and the dead time.";
                    ze:help "Show the OSPFv3 (IPv6) neighbors.";
                    container detail {
                        config false;
                        ze:command "ze-ospf:show-ospfv3-neighbor-detail";
                        description "Returns the advertised Interface ID, the DD sequence, the decoded
Options (R/V6/E/N/AF), the list sizes, the last NSM event, and the timers.";
                        ze:help "Show the full per-neighbor OSPFv3 state (spec-ospf-ext-14).";
                    }
                }
                container spf {
                    config false;
                    ze:command "ze-ospf:show-ospfv3-spf";
                    description "The history is read from the IPv6 unicast engine alone. Another
                                 address family is not covered here. A router that runs no OSPFv3
                                 engine answers an empty list rather than an error. That reads the
                                 same as a router whose engine has run no SPF yet.";
                    ze:help "Show the OSPFv3 (IPv6) per-area SPF run history.";
                    container detail {
                        config false;
                        ze:command "ze-ospf:show-ospfv3-spf-detail";
                        description "The command is read-only.";
                        ze:help "Explain why each OSPFv3 route won (spec-ospf-ext-14), AF/Instance-ID tagged.";
                    }
                }
            }

            container neighbor {
                config false;
                ze:command "ze-ospf:show-neighbor";
                description "Returns each neighbor's router-id, interface, adjacency state, DR/BDR,
priority, dead time, and address.";
                ze:help "Show OSPF neighbors.";
                container detail {
                    config false;
                    ze:command "ze-ospf:show-neighbor-detail";
                    description "Returns the DD sequence, the decoded Options including the RFC 5250
O-bit, the request and summary list sizes, the last NSM event, and the
timers.";
                    ze:help "Show the full per-neighbor state (spec-ospf-ext-14).";
                }
            }

            container interface {
                config false;
                ze:command "ze-ospf:show-interface";
                description "Returns area, network-type, cost, ISM state, DR/BDR, hello/dead intervals,
priority, and passive flag per interface.";
                ze:help "Show OSPF-enabled interfaces.";
                container detail {
                    config false;
                    ze:command "ze-ospf:show-interface-detail";
                    description "Returns the ISM state, the DR and BDR election detail, all three
timers, and the opaque-capable neighbor count.";
                    ze:help "Show the full per-interface state (spec-ospf-ext-14).";
                }
            }

            container database {
                config false;
                ze:command "ze-ospf:show-database";
                description "Lists each LSA with its LS Type, Link State ID, Advertising Router, sequence
number, age, and checksum.";
                ze:help "Show the OSPF link-state database.";

                container router {
                    config false;
                    ze:command "ze-ospf:show-database-router";
                    description "RFC 2328 Section 12.4.1 states that every router originates a Router-LSA.
The LSA describes the collected states of the router's interfaces to one area.
It is flooded throughout a single area only, and Ze reads the per-area store
for it.";
                    ze:help "Show only Router-LSAs (Type 1).";
                }
                container network {
                    config false;
                    ze:command "ze-ospf:show-database-network";
                    description "RFC 2328 Section 12.4.2 states that the Designated Router originates a
Network-LSA for a broadcast or NBMA network. The LSA lists the routers
connected to that network. It is flooded throughout a single area only. A
point-to-point link has no Designated Router, so it produces none.";
                    ze:help "Show only Network-LSAs (Type 2).";
                }
                container summary {
                    config false;
                    ze:command "ze-ospf:show-database-summary";
                    description "RFC 2328 Section 12.4.3 states that an area border router originates a
Summary-LSA. A Type 3 Summary-LSA describes a route to a network outside the
area and inside the AS. Ze reads the per-area store for it.";
                    ze:help "Show only Summary-LSAs (Type 3, inter-area network).";
                }
                container asbr-summary {
                    config false;
                    ze:command "ze-ospf:show-database-asbr-summary";
                    description "RFC 2328 Section 12.4.3 states that a Type 4 Summary-LSA describes a route
to an AS boundary router. A Type 3 describes a route to a network instead.
Both come from an area border router, and both are flooded through one area.";
                    ze:help "Show only ASBR-Summary-LSAs (Type 4).";
                }
                container external {
                    config false;
                    ze:command "ze-ospf:show-database-external";
                    description "RFC 2328 Section 12.4.4 states that an AS boundary router originates an
AS-external-LSA. The LSA describes a route to a destination in another
Autonomous System, and it is flooded throughout the AS. Ze reads the AS-wide
store for it, so no area appears in the answer.";
                    ze:help "Show only AS-external-LSAs (Type 5).";
                }
                container nssa-external {
                    config false;
                    ze:command "ze-ospf:show-database-nssa-external";
                    description "RFC 3101 Section 2.3 states that a Type 7 LSA is advertised only within a
single NSSA. A border router does not flood it into the backbone. It
translates selected Type 7 LSAs into Type 5 instead, so a translated route
appears under the AS-external view and not here.";
                    ze:help "Show only NSSA-external-LSAs (Type 7, RFC 3101).";
                }
                container opaque-link {
                    config false;
                    ze:command "ze-ospf:show-database-opaque-link";
                    description "RFC 5250 Section 3 gives link-state type-9 a link-local scope. A
                                 type-9 opaque LSA is not flooded beyond the local subnetwork. This
                                 view is therefore per link. No other link holds an LSA listed here,
                                 and no router past the local segment holds one.";
                    ze:help "Show only link-local opaque-LSAs (Type 9, RFC 5250).";
                    container detail {
                        config false;
                        ze:command "ze-ospf:show-database-opaque-link-detail";
                        description "A body with a typed decoder returns its TLVs, which are TE,
Router-Information, Extended and Segment-Routing. Every other body returns a
generic type, length and hex view (spec-ospf-ext-14).";
                        ze:help "Decode each link-local opaque LSA body (RFC 5250).";
                    }
                }
                container opaque-area {
                    config false;
                    ze:command "ze-ospf:show-database-opaque-area";
                    description "RFC 5250 Section 3 gives link-state type-10 an area-local scope: a
                                 type-10 opaque LSA is not flooded beyond the borders of its area.
                                 So this view is per area, and an area border router does not carry
                                 what it lists into the backbone.";
                    ze:help "Show only area-scope opaque-LSAs (Type 10, RFC 5250).";
                    container detail {
                        config false;
                        ze:command "ze-ospf:show-database-opaque-area-detail";
                        description "A body with a typed decoder returns its TLVs, which are TE,
Router-Information, Extended and Segment-Routing. Every other body returns a
generic type, length and hex view (spec-ospf-ext-14).";
                        ze:help "Decode each area-scope opaque LSA body (RFC 5250).";
                    }
                }
                container opaque-as {
                    config false;
                    ze:command "ze-ospf:show-database-opaque-as";
                    description "RFC 5250 Section 3 floods link-state type-11 throughout the
                                 autonomous system. It takes the scope of an AS-external (type-5)
                                 LSA. A type-11 opaque LSA reaches every transit area. It is not
                                 flooded into a stub area or an NSSA. A router does not originate
                                 one into a connected stub area or NSSA. One received from a
                                 neighbor inside such an area is rejected.";
                    ze:help "Show only AS-scope opaque-LSAs (Type 11, RFC 5250).";
                    container detail {
                        config false;
                        ze:command "ze-ospf:show-database-opaque-as-detail";
                        description "A body with a typed decoder returns its TLVs, which are TE,
Router-Information, Extended and Segment-Routing. Every other body returns a
generic type, length and hex view (spec-ospf-ext-14).";
                        ze:help "Decode each AS-scope opaque LSA body (RFC 5250).";
                    }
                }
                container router-information {
                    config false;
                    ze:command "ze-ospf:show-database-router-information";
                    description "OSPFv2 opaque type 4 and OSPFv3 function code 12, decoded into the
advertised informational capability bits and the TLV list.";
                    ze:help "Show the Router Information LSAs (RFC 7770) for both address families.";
                }
            }

            container te-database {
                config false;
                ze:command "ze-ospf:show-te-database";
                description "Router addresses plus TE links with their Link ID, local/remote address,
link type, TE metric, bandwidths, admin group, and (for inter-AS links) remote
AS and remote ASBR.";
                ze:help "Show the OSPF Traffic Engineering Database (RFC 3630 / RFC 5392).";
            }

            container route {
                config false;
                ze:command "ze-ospf:show-route";
                description "Lists each prefix with its path type (intra/inter/external-1/2), cost,
next-hops, and area.";
                ze:help "Show OSPF-computed routes.";

                container fast-reroute {
                    config false;
                    ze:command "ze-ospf:show-route-fast-reroute";
                    description "Lists each prefix's primary next-hops with their pre-computed loop-free
backup, protection class (node/link/downstream), and TI-LFA repair label
stack. Unprotected primaries are shown as unprotected.";
                    ze:help "Show OSPF fast-reroute (LFA / TI-LFA) backups (RFC 5286).";
                }
            }

            container virtual-links {
                config false;
                ze:command "ze-ospf:show-virtual-links";
                description "Lists each configured virtual link with its transit area, remote router-id,
adjacency state, computed cost, and transit next hop.";
                ze:help "Show OSPF virtual links (RFC 2328 section 15).";
            }

            container border-routers {
                config false;
                ze:command "ze-ospf:show-border-routers";
                description "Lists each reachable ABR/ASBR with its router-id, cost, next-hops, and area.";
                ze:help "Show routes to OSPF area-border and AS-boundary routers.";
            }

            container spf {
                config false;
                ze:command "ze-ospf:show-spf";
                description "Returns the most recent per-area SPF runs with their timestamp, duration, node
count, and pending state.";
                ze:help "Show recent OSPF SPF runs.";
                container detail {
                    config false;
                    ze:command "ze-ospf:show-spf-detail";
                    description "Returns the candidate paths considered for each prefix, the winning
cost, and the RFC 2328 section 16.4 path-preference tie-break. The command is
read-only, so the route table and the SPF run count do not change.";
                    ze:help "Explain why each route won the SPF calculation (spec-ospf-ext-14).";
                }
            }

            container ldp-sync {
                config false;
                ze:command "ze-ospf:show-ldp-sync";
                description "Lists each ldp-sync interface with its state (not-synchronized / hold-down /
synchronized), remaining hold-down, effective metric, and whether it is stuck
not-synchronized after having been synchronized.";
                ze:help "Show OSPF LDP-IGP synchronization state (RFC 5443, RFC 6138).";
            }
        }
    }

    container clear {
        config false;

        container ospf {
            config false;
            description "The subcommands drop adjacencies, zero counters or restart the process. None of
                         them edits the configuration, so a cleared router rebuilds the same state it held
                         before.";
            ze:help "Reset OSPF runtime state without reconfiguring.";

            container process {
                config false;
                description "clear ospf process alone is refused: say all to reset the whole
OSPF process. Everything is never the default.";
                ze:help "Full OSPF reset: all.";

                container all {
                    config false;
                    ze:command "ze-ospf:clear-process";
                    description "Every adjacency, in every configured instance, is torn down and SPF
re-runs over every area. Adjacencies re-form from the next Hello; the configuration is
unchanged.";
                    ze:help "Full OSPF reset: tear down every adjacency and re-run SPF.";
                }
            }

            container neighbor {
                config false;
                description "clear ospf neighbor alone is refused: say all to tear down every
adjacency. Everything is never the default.";
                ze:help "Tear down OSPF adjacencies: all.";

                container all {
                    config false;
                    ze:command "ze-ospf:clear-neighbor";
                    description "Adjacencies re-learn from the next Hello.";
                    ze:help "Tear down every OSPF adjacency so neighbors re-form.";
                }
            }

            container counters {
                config false;
                ze:command "ze-ospf:clear-counters";
                description "Monotonic Prometheus series are not reset; the SPF-run log is cleared.";
                ze:help "Reset the OSPF SPF-run history.";
            }
        }
    }

    container request {
        config false;

        container ospf {
            config false;
            description "The actions run against the live process and change no configuration. A router
                         restarted after one of them comes back to the state its config describes.";
            ze:help "OSPFv2 operational actions (RFC 2328).";

            container graceful-restart {
                config false;
                ze:command "ze-ospf:graceful-restart-prepare";
                description "The engine originates one Grace-LSA per interface, persists the non-volatile
restart fact, and suppresses route churn so the FIB is retained across the
ensuing control-plane restart. Refused when graceful-restart is not
configured.";
                ze:help "Trigger a planned OSPFv2 graceful restart (RFC 3623 section 2.1).";
            }
        }
    }

    container debug {
        config false;
        description "Denied by the read-only authz profile and off by default; a testing/research
facility that injects a crafted LSA into this router's LSDB, which then floods
normally.";
        ze:help "OSPF debug LSA injection (spec-ospf-ext-14).";

        container ip {
            config false;
            description "These act on OSPFv2 alone. The OSPFv3 equivalents are under debug ipv6, and the
                         controls that hold for both families are under debug ospf.";
            ze:help "IPv4 OSPF debug commands.";
            container ospf {
                config false;
                description "The scope is the IPv4 address family. A router that also runs OSPFv3 keeps that
                             instance untouched by anything here.";
                ze:help "OSPFv2 debug commands.";
                container inject {
                    config false;
                    description "Injection is refused until debug ospf inject is enabled, so the command cannot
                                 fire on a router nobody armed. It exists to drive a decoder against an LSA a real
                                 neighbor is unlikely to send.";
                    ze:help "Inject crafted OSPFv2 LSAs for testing.";
                    container opaque {
                        config false;
                        ze:command "ze-ospf:debug-inject";
                        description "The default Opaque Type is Private-Use so a test LSA never collides with a
standards-track consumer. Requires `debug ospf inject enable`.";
                        ze:help "Inject a crafted IPv4 opaque LSA into the local LSDB (RFC 5250).";

                        container scope {
                            config false;
                            ze:modifier "required";
                            description "The keyword is required and takes link, area or as. Any other word is
refused. For link scope Ze uses the first configured interface.";
                            ze:help "Flooding scope of the injected LSA.";
                            leaf scope {
                                type enumeration {
                                    enum link { ze:help "Opaque type 9, flooded on one link only."; }
                                    enum area { ze:help "Opaque type 10, flooded inside the area."; }
                                    enum as { ze:help "Opaque type 11, flooded across the AS."; }
                                }
                                mandatory true;
                                description "The word selects the opaque LSA type Ze originates. Any other word is
refused with the three accepted words in the message.";
                                ze:help "Link-local, area, or AS flooding scope.";
                            }
                        }
                        container id {
                            config false;
                            ze:modifier "required";
                            description "The keyword is required and the value is a 24-bit number, so 16777215 is the
largest. A larger number is refused with 'opaque id exceeds 24 bits (max
16777215)'.";
                            ze:help "Opaque ID of the injected LSA.";
                            leaf opaque-id {
                                type uint32 {
                                    range "0..16777215";
                                }
                                mandatory true;
                                description "The value is decimal. With the Opaque Type it forms the Link State ID
of the injected LSA, so a withdraw MUST repeat the same value.";
                                ze:help "24-bit Opaque ID (RFC 5250 Appendix A.2).";
                            }
                        }
                        container type {
                            config false;
                            ze:modifier "once";
                            description "Defaults to a Private-Use type so a test LSA never collides with a
standards-track consumer.";
                            ze:help "Opaque Type of the injected LSA.";
                            leaf type {
                                type uint8 {
                                    range "128..255";
                                }
                                mandatory true;
                                description "The value is decimal and Ze refuses one below 128 or above 255. When
the keyword is absent the LSA takes the Private-Use default.";
                                ze:help "Private-Use Opaque Type (RFC 5250 Section 9).";
                            }
                        }
                        container hex {
                            config false;
                            ze:modifier "repeat";
                            description "Repeat the keyword to append more octets, and mix it with tlv freely: the
body grows in the order the keywords are typed. Ze refuses a body longer than
the LSA maximum, which is 65535 bytes minus the 20-octet header.";
                            ze:help "Raw body octets, appended in the order supplied.";
                            leaf body {
                                type string {
                                    pattern "[0-9a-fA-F]*";
                                }
                                mandatory true;
                                description "The value is an even number of hex digits with no prefix and no
separator. Ze decodes it and appends the octets to the LSA body.";
                                ze:help "Body octets as hex.";
                            }
                        }
                        container tlv {
                            config false;
                            ze:modifier "repeat";
                            description "Ze builds the TLV from a decimal type and a hex value. It writes the
2-byte type and the 2-byte length, then pads the result with zeros to a
multiple of 4 octets. Repeat the keyword to append more TLVs.";
                            ze:help "One 4-octet-aligned opaque TLV, appended to the body.";
                            leaf type {
                                type uint16;
                                mandatory true;
                                description "The value is decimal. Ze writes it into the 2-octet type field of
the TLV.";
                                ze:help "TLV type.";
                            }
                            leaf value-hex {
                                type string {
                                    pattern "[0-9a-fA-F]*";
                                }
                                mandatory true;
                                description "The value is an even number of hex digits with no prefix. Its decoded
length fills the 2-octet length field, and Ze pads the octets with zeros to a multiple
of 4.";
                                ze:help "TLV value as hex.";
                            }
                        }
                        container withdraw {
                            config false;
                            ze:modifier "once";
                            description "Ze reoriginates the LSA at MaxAge, which is what tells the neighbors to
remove it. The scope and the id still select which LSA goes, so pass the same
pair the origination used.";
                            ze:help "MaxAge-flush the LSA instead of originating it.";
                        }
                    }
                }
            }
        }

        container ipv6 {
            config false;
            description "These act on OSPFv3 alone. The OSPFv2 equivalents are under debug ip, and the
                         controls that hold for both families are under debug ospf.";
            ze:help "IPv6 OSPF debug commands.";
            container ospf {
                config false;
                description "The scope is the IPv6 address family. A router that also runs OSPFv2 keeps that
                             instance untouched by anything here.";
                ze:help "OSPFv3 debug commands.";
                container inject {
                    config false;
                    description "Injection is refused until debug ospf inject is enabled, so the command cannot
                                 fire on a router nobody armed. It exists to drive a decoder against an LSA a real
                                 neighbor is unlikely to send.";
                    ze:help "Inject crafted OSPFv3 LSAs for testing.";
                    container lsa {
                        config false;
                        ze:command "ze-ospf:debug-ospfv3-inject";
                        description "The flooding scope is derived from the LS Type S2/S1 bits (a reserved scope is
rejected). Requires `debug ospf inject enable`.";
                        ze:help "Inject a crafted OSPFv3 LSA into the local LSDB (RFC 5340).";

                        container type {
                            config false;
                            ze:modifier "required";
                            description "Its S2/S1 bits carry the flooding scope, which is why the scope keyword is a
cross-check and not the source.";
                            ze:help "LS Type of the injected LSA.";
                            leaf ls-type {
                                type string {
                                    pattern "(0[xX])?[0-9a-fA-F]{1,4}";
                                }
                                mandatory true;
                                description "The 0x prefix is optional. Bits S2 and S1 of the value give the
flooding scope, and Ze refuses the reserved combination 11 (RFC 5340 Appendix A.4.2.1).";
                                ze:help "16-bit LS Type in hex, such as 0x2009.";
                            }
                        }
                        container id {
                            config false;
                            ze:modifier "required";
                            description "The keyword is required and the value is a 32-bit number. The Link State ID
and the LS Type together select the LSA. A withdraw MUST repeat the same pair
the origination used.";
                            ze:help "Link State ID of the injected LSA.";
                            leaf link-state-id {
                                type uint32;
                                mandatory true;
                                description "The value is decimal. Ze writes it into the Link State ID field of the
LSA header, where OSPFv3 gives it no address meaning.";
                                ze:help "32-bit Link State ID.";
                            }
                        }
                        container scope {
                            config false;
                            ze:modifier "once";
                            description "Supplying a scope that disagrees with the LS Type is refused; supplying none
accepts the LS Type.";
                            ze:help "Cross-check on the scope the LS Type states.";
                            leaf scope {
                                type enumeration {
                                    enum link { ze:help "Expect S2/S1 bits 00, flooded on one link only."; }
                                    enum area { ze:help "Expect S2/S1 bits 01, flooded inside the area."; }
                                    enum as { ze:help "Expect S2/S1 bits 10, flooded across the AS."; }
                                }
                                mandatory true;
                                description "Ze compares the word with the scope the LS Type bits state and refuses
the command when the two disagree. The word never sets the scope by itself.";
                                ze:help "Link-local, area, or AS flooding scope.";
                            }
                        }
                        container hex {
                            config false;
                            ze:modifier "repeat";
                            description "Repeat the keyword to append more octets, and the body grows in the order
the keywords are typed. OSPFv3 takes no tlv keyword here, so a structured body
is written as hex.";
                            ze:help "Raw body octets, appended in the order supplied.";
                            leaf body {
                                type string {
                                    pattern "[0-9a-fA-F]*";
                                }
                                mandatory true;
                                description "The value is an even number of hex digits with no prefix and no
separator. Ze decodes it and appends the octets to the LSA body, which is refused above
65515 octets.";
                                ze:help "Body octets as hex.";
                            }
                        }
                        container withdraw {
                            config false;
                            ze:modifier "once";
                            description "Ze reoriginates the LSA at MaxAge, which is what tells the neighbors to
remove it. A link-local LSA is withdrawn from the per-interface store, and any
other scope is withdrawn from the backbone area store.";
                            ze:help "MaxAge-flush the LSA instead of originating it.";
                        }
                    }
                }
            }
        }

        container ospf {
            config false;
            description "What is set here holds for OSPFv2 and OSPFv3 together. A control that binds one
                         family alone lives under debug ip or debug ipv6.";
            ze:help "Address-family-independent OSPF debug controls.";
            container inject {
                config false;
                description "It is the arming switch both injection commands read. Injection stays refused
                             while it is off, so a router is never one typo away from a crafted LSA.";
                ze:help "Enable or disable OSPF debug LSA injection.";
                container enable {
                    config false;
                    ze:command "ze-ospf:debug-inject-enable";
                    description "Off by default.";
                    ze:help "Enable OSPF debug LSA injection (shared across both address families).";
                }
                container disable {
                    config false;
                    ze:command "ze-ospf:debug-inject-disable";
                    description "One flag covers both address families, so this stops IPv4 and IPv6
injection together. An inject after it fails with 'debug injection not enabled
(run `debug ospf inject enable`)'. The flag is never written to the config, so
a reboot returns the router to injection off.";
                    ze:help "Disable OSPF debug LSA injection.";
                }
            }
        }
    }
}
