module ze-ldp-cmd {
    namespace "urn:ze:ldp:cmd";
    prefix ldpcmd;
    import ze-extensions { prefix ze; }
    // Removing the component removes these command nodes together with the
    // handlers. See ai/rules/plugin-self-containment.md.
    description "The show ldp command tree, owned by the ldp component.";
    revision 2026-06-03 { description "Relocated show ldp ... out of the central show schema (plugin self-containment)."; }

    container show {
        config false;
        ze:help "Read-only commands to inspect system, protocol, and network state.";

        container ldp {
            config false;
            description "A binding can exist for a neighbor that is not the next hop, because LDP
                         distributes labels regardless of which one the routing table chose.";
            ze:help "LDP neighbors and label bindings.";

            container neighbor {
                config false;
                ze:command "ze-ldp:show-neighbor";
                description "Returns peer address, transport address, session state, and hold time for each
LDP neighbor.";
                ze:help "Show LDP neighbors and their session state.";
            }

            container binding {
                config false;
                ze:command "ze-ldp:show-binding";
                description "Lists local and remote label bindings for each FEC (prefix). Use this to
verify label distribution is working.";
                ze:help "Show LDP FEC-to-label bindings.";
            }
        }
    }
}
