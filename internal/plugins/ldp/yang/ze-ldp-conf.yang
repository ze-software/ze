module ze-ldp-conf {
    namespace "urn:ze:ldp:conf";
    prefix ldpconf;
    import ze-extensions { prefix ze; }
    description "LDP protocol configuration (RFC 5036)";
    revision 2026-05-28 { description "Initial revision"; }

    container ldp {
        description "The engine stays idle until lsr-id carries an address, and it says so in
                     the log. Ze then sends Hello messages to 224.0.0.2 port 646 and opens a TCP
                     session on port 646 to each neighbor it discovers.";
        ze:help "Label Distribution Protocol configuration";

        leaf lsr-id {
            type string;
            description "Ze refuses a value that is not an IP address, and stays idle while the
                         leaf is empty. The first 4 bytes of every LDP PDU header carry this
                         identifier. Ze also originates a label binding for the address itself,
                         so a neighbor can reach this LSR by its identifier.";
            ze:help "LSR identifier (IPv4 address format)";
        }

        leaf transport-address {
            type string;
            description "Ze advertises this address in the transport address TLV of each Hello,
                         which is the address a neighbor connects to. Ze also binds it as the
                         source address of the TCP connection it opens. With the leaf empty, the
                         Hello carries no transport address TLV and the kernel picks the source
                         address.";
            ze:help "Transport address for TCP sessions";
        }

        leaf hello-interval {
            type uint16 {
                range "1..65535";
            }
            default 5;
            units seconds;
            description "The default is 5 seconds and the range is 1 to 65535. Ze sends one
                         Hello for each interface at this period. A shorter interval finds a
                         neighbor faster and puts more packets on the link.";
            ze:help "Hello message interval";
        }

        leaf hello-hold-time {
            type uint16 {
                range "1..65535";
            }
            default 15;
            units seconds;
            description "The default is 15 seconds, which is 3 hello intervals. Ze advertises
                         this value in each Hello, and a neighbor drops the adjacency when no
                         Hello arrives inside it. Keep it more than hello-interval, because a hold time
                         under one interval drops the adjacency between two Hellos.";
            ze:help "Hello adjacency hold time";
        }

        leaf keepalive-time {
            type uint16 {
                range "1..65535";
            }
            default 60;
            units seconds;
            description "The default is 60 seconds and the range is 1 to 65535. RFC 5036
                         section 3.5.3 carries the KeepAlive Time in the Common Session
                         Parameters of the Initialization message. The receiving LSR MUST
                         calculate the KeepAlive Timer from 'the smaller of its proposed
                         KeepAlive Time and the KeepAlive Time received in the PDU'.
                         The lower of the two proposals wins. Ze proposes this value to each
                         neighbor it opens a session to. Ze sends a KeepAlive every third of
                         the negotiated value and closes the session when no PDU arrives
                         inside three times it. The exchange happens one time, at the start
                         of the session, so a session that is up keeps the value it
                         negotiated. A change here applies to the sessions that open after
                         it.";
            ze:help "Session keepalive interval.";
        }

        leaf hop-count-max {
            type uint8 {
                range "1..255";
            }
            default 254;
            description "The default is 254 and the range is 1 to 255. RFC 5036 section
                         3.4.4.1 makes an LSR check the Hop Count TLV of a received message
                         against 'its configured maximum allowable value'. A Label Mapping
                         whose hop count exceeds this value is answered with a Loop Detected
                         Notification and its label is not used. A change here applies to
                         the sessions that open after it.";
            ze:help "Maximum hop count a Label Mapping can carry.";
        }

        leaf-list interfaces {
            type string;
            description "Ze runs one discovery listener for each interface of this list. An
                         empty list runs one listener that the system assigns to an interface
                         itself. A reload starts discovery on an interface added to the list and
                         stops it on one removed, and it leaves the other interfaces alone. The
                         connected prefixes of these interfaces are the FECs this LSR is egress
                         for.";
            ze:help "Interfaces on which LDP discovery is enabled";
        }
    }
}
