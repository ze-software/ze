module ze-routing-table-conf {
    namespace "urn:ze:routing-table:conf";
    prefix routing-table;

    import ze-extensions { prefix ze; }

    description
        "Named routing table registry for Ze.
         Maps human-readable names to kernel table IDs.
         Used by static routes and policy routing to reference
         tables by name. The name 'default' is built-in and
         maps to table 0 (kernel RT_TABLE_MAIN 254).";

    revision 2026-05-15 {
        description "Initial revision.";
    }

    container routing-table {
        description
            "Ze builds one registry from these entries, and a static route or a policy
             route resolves its table name against that registry. The name default is
             built-in and resolves to table 0, so no entry can carry that name.";
        ze:help "Named routing table definitions. Each entry maps
                 a name to a kernel routing table ID.";

        list table {
            key "name";
            description "One entry maps one name to one kernel table identifier. Ze refuses an
                         entry named default, and refuses an entry with no id. Two entries CAN
                         carry the same identifier, because the registry keys on the name.";
            ze:help "A named routing table.";

            leaf name {
                type string;
                description
                    "The name is the list key, and it is the value a static route or a
                     policy route carries in its table leaf. A route that names a table
                     no entry defines is refused when Ze resolves it.";
                ze:help "Table name referenced by static routes
                         and policy routing configuration.";
            }

            leaf id {
                type uint32 {
                    range "1..252 | 256..4294967295";
                }
                mandatory true;
                description
                    "The leaf is mandatory. The range refuses 0 and 253 to 255, because
                     253 is the kernel default table, 254 is the main table and 255 is
                     the local table. Ze also refuses an identifier inside a range Ze
                     reserves for its own tables (internal/core/iprule, ZeTableRanges:
                     VRF tables, policy routing auto tables, IPsec source-guard tables),
                     and an identifier this build cannot
                     program through netlink without truncation.";
                ze:help "Kernel routing table ID; not 0, 253-255 or a range Ze reserves";
            }
        }
    }
}
