module ze-traffic-cmd {
    namespace "urn:ze:traffic:cmd";
    prefix trafficcmd;
    import ze-extensions { prefix ze; }
    // The handler reads traffic.GetBackend(). The command container-merges onto
    // the show verb root, under the shared `traffic` namespace.
    // See ai/rules/plugin-self-containment.md.
    description "The show traffic control (QoS) command, owned by the traffic component.";
    // traffic becomes a namespace shared with show traffic usage.
    revision 2026-07-02 { description "Nest under show traffic control, which was show traffic."; }
    // It left the central show schema, for plugin self-containment.
    revision 2026-06-03 { description "Relocate show traffic into the traffic component."; }

    container show {
        config false;
        ze:help "Read-only commands to inspect system, protocol, and network state.";

        container traffic {
            config false;
            description "Two different things share this noun: QoS decides how packets are scheduled, and
                         usage accounting counts bytes per subscriber. Neither one reads the other.";
            ze:help "Traffic subsystem: QoS control and byte-usage accounting.";

            container control {
                config false;
                ze:command "ze-traffic:show-traffic";
                ze:rpc "ze-cli-show-api:traffic";
                description "Without arguments, lists every interface with its qdisc type and class/filter
counts. With an interface name, shows the full qdisc and class breakdown. Use
this to verify your shaping is applied.";
                ze:help "Show traffic control (QoS) configuration per interface.";
            }
        }
    }
}
