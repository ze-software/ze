module ze-mpls-cmd {
    namespace "urn:ze:mpls:cmd";
    prefix mplscmd;
    import ze-extensions    { prefix ze; }
    import ze-cli-show-cmd  { prefix clishowcmd; }
    // Relocated from the central show schema, for plugin self-containment.
    description "MPLS show commands: forwarding table inspection.";
    // It replaces a handler-side row-limit flag.
    revision 2026-11-12 { description "Read the table of the data plane interface backend selects, the kernel or VPP."; }
    revision 2026-06-26 { description "Add the row-cap as a 'limit' keyword leaf, matching show route."; }
    revision 2026-06-03 { description "Initial revision: relocated from ze-cli-show-cmd."; }

    augment "/clishowcmd:show" {
        container mpls {
            config false;
            description "This is the forwarding state the dataplane uses. The protocol that installed a
                         label lives under show ldp or show rsvp-te.";
            ze:help "MPLS forwarding table and label operations.";

            container forwarding {
                config false;
                ze:command "ze-mpls:show-forwarding";
                description "Each entry shows the incoming label, swap/push/pop operation, and outgoing
next-hop. Ze reads the data plane that 'interface backend' selects: the kernel MPLS
table, or VPP MPLS table 0. Pass 'limit N' to cap large tables.";
                ze:help "Show MPLS forwarding entries installed in the data plane.";
                leaf limit {
                    type uint32;
                    description "The value is a positive integer. Ze returns at most that many
entries and sets truncated to true when the data plane holds more. Absent, the value
is 100000.";
                    ze:help "Maximum number of entries.";
                }
            }
        }
    }
}
