module ze-fakeas112-cmd {
    namespace "urn:ze:test:fakeas112:cmd";
    prefix fakeas112cmd;
    import ze-extensions { prefix ze; }
    description "Test-only synthetic AS112 route producer command tree.
                 Hidden behind ze:hidden so it does not pollute the
                 production CLI completion when an operator runs
                 `ze cli` against a daemon that loaded fakeas112.";
    revision 2026-07-05 { description "Initial revision."; }

    container fakeas112 {
        ze:hidden true;
        config false;
        description "The plugin drives the AS112 redistribute producer namespace on
demand. A .ci test can then exercise the bgp-redistribute origin-AS and
community path, and the real AS112 DNS engine stays stopped. ze:hidden keeps
this subtree out of the production CLI completion.";
        ze:help "Fakeas112 test commands.";

        container emit {
            config false;
            ze:command "ze-test-fakeas112:emit";
            ze:rpc "ze-fakeas112-api:fakeas112-emit";
            description "The four covering prefixes are 192.175.48.0/24,
192.31.196.0/24, 2620:4f:8000::/48 and 2001:4:112::/48. One batch goes out per
family, tagged with the origin ASN, which is 112 without an asn value. The
/32 and /128 host addresses bound on lo are never emitted.";
            ze:help "Emit the AS112 covering prefixes as route-change batches.";
        }

        container help {
            config false;
            ze:command "ze-test-fakeas112:help";
            ze:rpc "ze-fakeas112-api:fakeas112-help";
            description "The answer is one usage line, as a plain string. It names
the add and del actions and the family, asn and community keywords that
'fakeas112 emit' takes.";
            ze:help "Print the fakeas112 command surface.";
        }
    }
}
