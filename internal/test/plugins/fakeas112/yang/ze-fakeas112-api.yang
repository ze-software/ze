module ze-fakeas112-api {
  namespace "urn:ze:test:fakeas112:api";
  prefix "fakeas112-api";

  import ze-extensions { prefix ze; }

  organization "Ze Project";
  // fakeas112 emits route-change events on the as112 namespace, which is the
  // same handle the real producer uses. A .ci test can then exercise the
  // bgp-redistribute origin-AS and community path without starting the AS112
  // DNS engine.
  description "Test-only synthetic AS112 route producer RPCs.";
  revision 2026-07-05 {
    description "Initial revision -- emit / help.";
  }

  rpc fakeas112-emit {
    description "Args: <add|del> [asn <N>] [community <c1,c2,...>].";
    ze:help "Emit the AS112 covering prefixes as one route-change batch per family.";
  }

  rpc fakeas112-help {
    description "The answer is one fixed line naming the emit form and its options. It is a
constant of the test plugin, so it does not read the command registry.";
    ze:help "Print the fakeas112 command surface.";
  }
}
