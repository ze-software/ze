module ze-fakeredist-api {
  namespace "urn:ze:test:fakeredist:api";
  prefix "fakeredist-api";

  import ze-extensions { prefix ze; }

  organization "Ze Project";
  description "Test-only synthetic redistribute producer RPCs.
               fakeredist exposes these so .ci scenarios can drive the
               bgp-redistribute-egress consumer without waiting for a real
               protocol producer (L2TP, connected, ...) to land.";
  revision 2026-04-19 {
    description "Initial revision -- emit / emit-burst / help.";
  }

  revision 2026-09-04 {
    description "Add consume / consumed: a synthetic consumer a scenario registers
                 on demand, so the late-consumer replay has a destination to
                 land in.";
  }

  rpc fakeredist-emit {
    description "Args: <add|remove> <family> <prefix> [<nexthop>].";
    ze:help "Emit one synthetic route-change batch.";
  }

  rpc fakeredist-emit-burst {
    description "Args: <N> <add|remove> <family> <base-prefix>. N is bounded to one million per
call.";
    ze:help "Emit N synthetic batches with the host portion of the base prefix auto-incremented.";
  }

  rpc fakeredist-consume {
    description "Args: <destination-name>. The consumer records every route the
orchestrator dispatches to it, so a .ci scenario can register one AFTER a
producer emitted and read back what the replay delivered.";
    ze:help "Register a synthetic redistribution consumer under a name.";
  }

  rpc fakeredist-consumed {
    description "Args: <destination-name>. The answer carries 'prefixes', the sorted
prefix list, and 'count'.";
    ze:help "List the prefixes a synthetic consumer currently holds.";
  }

  rpc fakeredist-help {
    description "The answer is one JSON object with a single key, help. That key
holds two usage lines, one for fakeredist emit and one for fakeredist
emit-burst.";
    ze:help "Print the fakeredist command surface.";
  }
}
