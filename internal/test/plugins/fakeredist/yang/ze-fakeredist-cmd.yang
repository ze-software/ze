module ze-fakeredist-cmd {
    namespace "urn:ze:test:fakeredist:cmd";
    prefix fakeredistcmd;
    import ze-extensions { prefix ze; }
    description "Test-only synthetic redistribute producer command tree.
                 Hidden behind ze:hidden so it does not pollute the
                 production CLI completion when an operator runs
                 `ze cli` against a daemon that loaded fakeredist.";
    revision 2026-04-19 { description "Initial revision."; }
    revision 2026-09-04 { description "Add consume / consumed."; }

    container fakeredist {
        ze:hidden true;
        config false;
        description "The tree carries ze:hidden, so it does not reach an operator's completion when
'ze cli' runs against a daemon that loaded fakeredist. The plugin ships in the
production composition root all the same, which is why emit-burst carries an
upper bound.";
        ze:help "Fakeredist test commands.";

        container emit {
            config false;
            ze:command "ze-test-fakeredist:emit";
            ze:rpc "ze-fakeredist-api:fakeredist-emit";
            description "The arguments are 'add' or 'remove', an address family, a prefix, and an
optional next hop. The batch carries one entry. The answer carries 'delivered',
the number of consumers that received it.";
            ze:help "Emit one synthetic route-change batch.";
        }

        container emit-burst {
            config false;
            ze:command "ze-test-fakeredist:emit-burst";
            ze:rpc "ze-fakeredist-api:fakeredist-emit-burst";
            description "The arguments are the count, 'add' or 'remove', an address family, and a base
prefix. The count MUST be a positive integer no larger than 1000000. Each step
keeps the prefix length and increments the address, so a peer sees that many
distinct prefixes.";
            ze:help "Emit N synthetic batches sequentially.";
        }

        container consume {
            config false;
            ze:command "ze-test-fakeredist:consume";
            ze:rpc "ze-fakeredist-api:fakeredist-consume";
            description "The argument is the destination name to register under. It MUST differ from
'fakeredist', because a protocol is never redistributed into itself. Registering
one after a producer emitted is what the late-consumer replay is asked to
repair.";
            ze:help "Register a synthetic redistribution consumer.";
        }

        container consumed {
            config false;
            ze:command "ze-test-fakeredist:consumed";
            ze:rpc "ze-fakeredist-api:fakeredist-consumed";
            description "The argument is the destination name. The answer carries 'prefixes', the
sorted prefix list the consumer was given, and 'count'.";
            ze:help "List the prefixes a synthetic consumer holds.";
        }

        container help {
            config false;
            ze:command "ze-test-fakeredist:help";
            ze:rpc "ze-fakeredist-api:fakeredist-help";
            description "The answer is the two usage lines of the plugin: 'fakeredist emit add|remove
<family> <prefix> [<nexthop>]' and 'fakeredist emit-burst <N> add|remove
<family> <base-prefix>'.";
            ze:help "Print the fakeredist command surface.";
        }
    }
}
