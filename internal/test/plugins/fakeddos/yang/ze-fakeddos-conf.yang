module ze-fakeddos-conf {
  namespace "urn:ze:fakeddos-conf";
  prefix fakeddos;

  import ze-ddos-detect-conf { prefix dd; }
  import ze-extensions { prefix ze; }

  description "Test-only synthetic DDoS injector configuration. Augments the shared
               `ddos` container (owned by ze-ddos-detect-conf) with a `fake` subtree
               whose presence starts the injector (see internal/test/plugins/fakeddos).
               Compiled only under the zetest build tag, so production never sees it.";
  revision 2026-07-13 { description "Initial: presence container ddos/fake driving the ddos-local withdraw functional test."; }

  augment "/dd:ddos" {
    container fake {
      presence "Configure the synthetic DDoS attack injector (test-only).";
      leaf enabled {
        type boolean;
        default false;
        description "When true, the injector emits a synthetic AttackDetected event.
                     It then emits AttackCleared on the driver's trigger.
                     The default false leaves the injector inert.";
        ze:help "Start the synthetic DDoS injector. The default false leaves it inert.";

      }
    }
  }
}
