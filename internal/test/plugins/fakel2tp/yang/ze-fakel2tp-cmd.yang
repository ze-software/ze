module ze-fakel2tp-cmd {
    namespace "urn:ze:test:fakel2tp:cmd";
    prefix fakel2tpcmd;
    import ze-extensions { prefix ze; }
    // ze:hidden hides the tree, so it does not reach the production CLI
    // completion.
    description "Test-only synthetic L2TP route producer command tree.";
    revision 2026-04-21 { description "Initial revision."; }

    container fakel2tp {
        ze:hidden true;
        config false;
        description "The tree carries ze:hidden, so it does not reach an operator's completion. The
plugin emits route-change events on the l2tp namespace. A .ci test drives the
bgp-redistribute consumer through them, with no kernel module, no UDP listener
and no PPP.";
        ze:help "Fakel2tp test commands.";

        container emit {
            config false;
            ze:command "ze-test-fakel2tp:emit";
            ze:rpc "ze-fakel2tp-api:fakel2tp-emit";
            description "The arguments are 'add' or 'remove', an address family, and a prefix. The batch
carries one entry and it goes out under the l2tp protocol ID. The answer carries
'delivered', the number of consumers that received it.";
            ze:help "Emit one synthetic L2TP route-change batch.";
        }

        container help {
            config false;
            ze:command "ze-test-fakel2tp:help";
            ze:rpc "ze-fakel2tp-api:fakel2tp-help";
            description "The answer is the one usage line of the plugin: 'fakel2tp emit add|remove
<family> <prefix>'.";
            ze:help "Print the fakel2tp command surface.";
        }
    }
}
