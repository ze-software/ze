module ze-fakel2tp-api {
  namespace "urn:ze:test:fakel2tp:api";
  prefix "fakel2tp-api";

  import ze-extensions { prefix ze; }

  organization "Ze Project";
  description "Test-only synthetic L2TP route producer RPCs.
               fakel2tp emits route-change events on the l2tp namespace
               so .ci tests can exercise the bgp-redistribute consumer
               without a real L2TP subsystem.";
  revision 2026-04-21 {
    description "Initial revision -- emit / help.";
  }

  rpc fakel2tp-emit {
    description "Args: <add|remove> <family> <prefix>.";
    ze:help "Emit one synthetic L2TP route-change batch.";
  }

  rpc fakel2tp-help {
    description "The answer is the one usage line of the plugin: 'fakel2tp emit add|remove
<family> <prefix>'. The plugin declares no other command.";
      ze:help "Print the fakel2tp command surface.";
  }
}
