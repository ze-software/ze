module ze-system-cmd {
    namespace "urn:ze:system:cmd";
    prefix syscmd;

    import ze-extensions { prefix ze; }

    description
        "System operational command tree for Ze CLI.
         Covers system introspection and daemon lifecycle commands.";

    revision 2026-03-16 {
        description "Initial revision";
    }

    revision 2026-06-04 {
        description "Verb-first grammar: process reads under show, lifecycle actions under request.";
    }

    // System group

    container system {
        config false;
        description "System operations";

        container help {
            config false;
            ze:command "ze-system:help";
            description "Show available commands";
        }

        container dispatch {
            config false;
            ze:command "ze-system:dispatch";
            description "Dispatch a text command";
        }

        container version {
            config false;
            description "Version information";

            container software {
                config false;
                ze:command "ze-system:version-software";
                description "Show ze version";
            }

            container api {
                config false;
                ze:command "ze-system:version-api";
                description "Show IPC protocol version";
            }
        }

        container subsystem {
            config false;
            description "Subsystem operations";

            container list {
                config false;
                ze:command "ze-system:subsystem-list";
                description "List available subsystems";
            }
        }

        container command {
            config false;
            description "Command introspection";

            container list {
                config false;
                ze:command "ze-system:command-list";
                description "List all commands";
            }

            container help {
                config false;
                ze:command "ze-system:command-help";
                description "Show command details";
            }

            container complete {
                config false;
                ze:command "ze-system:command-complete";
                description "Complete command/args";
            }
        }
    }

    // Process status

    container show {
        config false;
        description "Read-only process inspection";

        container status {
            config false;
            ze:command "ze-system:daemon-status";
            description "Show process status, uptime, and resource usage.";
        }
    }

    // Process lifecycle actions

    container request {
        config false;
        description "Process lifecycle actions";

        container shutdown {
            config false;
            ze:command "ze-system:daemon-shutdown";
            description "Gracefully shutdown: drain connections, close peers, exit.";
        }

        container reboot {
            config false;
            ze:command "ze-system:daemon-reboot";
            description "Gracefully shutdown then reboot the system.";
        }

        container halt {
            config false;
            ze:command "ze-system:daemon-quit";
            description "Dump goroutine stacks to stderr and terminate immediately.";
        }

        container reload {
            config false;
            ze:command "ze-system:daemon-reload";
            description "Reload the configuration without restarting.";
        }
    }
}
