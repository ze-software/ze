module ze-plugin-engine {
    namespace "urn:ze:plugin:engine";
    prefix engine;

    import ze-types { prefix zt; }

    description
        "RPCs served by the engine for plugins to call (Socket A).
         Plugins use these RPCs during startup and runtime to register,
         declare capabilities, signal readiness, and inject routes.";

    revision 2026-02-01 {
        description "Initial revision";
    }

    // Stage 1: Plugin declares itself to the engine.

    rpc declare-registration {
        description
            "Plugin declares families, commands, config wants, and YANG schema.
             Called during Stage 1 of the 5-stage startup protocol.";
        input {
            list family {
                key "name";
                leaf name {
                    type string;
                    description "Address family (e.g., ipv4/unicast, l2vpn/evpn)";
                }
                leaf mode {
                    type enumeration {
                        enum encode { description "Encode text to wire"; }
                        enum decode { description "Decode wire to JSON"; }
                        enum both { description "Encode and decode"; }
                    }
                    description "Family handling mode";
                }
            }
            list command {
                key "name";
                leaf name {
                    type string;
                    description "Command name";
                }
                leaf description {
                    type string;
                    description "Command description";
                }
                leaf-list args {
                    type string;
                    description "Argument names";
                }
                leaf completable {
                    type boolean;
                    default false;
                    description "Supports tab completion";
                }
            }
            leaf-list wants-config {
                type string;
                description "Config roots to receive (e.g., bgp, environment, *)";
            }
            container schema {
                description "YANG schema declaration";
                leaf module {
                    type string;
                    description "YANG module name";
                }
                leaf namespace {
                    type string;
                    description "YANG namespace URI";
                }
                leaf yang-text {
                    type string;
                    description "Full YANG module text";
                }
                leaf-list handlers {
                    type string;
                    description "Handler paths (e.g., bgp, bgp.peer)";
                }
            }
            list filter {
                key "name";
                description
                    "Named route filters this plugin offers.
                     Config references by name in filter { import/export } blocks.";
                leaf name {
                    type string;
                    description "Filter name (the part after : in <plugin>:<filter>)";
                }
                leaf direction {
                    type enumeration {
                        enum import { description "Ingress filtering"; }
                        enum export { description "Egress filtering"; }
                        enum both { description "Ingress and egress filtering"; }
                    }
                    description "Which direction(s) this filter handles";
                }
                leaf-list attributes {
                    type string;
                    description "Attribute names to receive (e.g., as-path, community)";
                }
                leaf nlri {
                    type boolean;
                    default true;
                    description "Whether to include NLRI list in filter input";
                }
                leaf raw {
                    type boolean;
                    default false;
                    description "Whether to include raw wire bytes";
                }
                leaf on-error {
                    type enumeration {
                        enum reject { description "Fail-closed: drop update on error"; }
                        enum accept { description "Fail-open: pass update on error"; }
                    }
                    default reject;
                    description "Behavior when filter IPC fails";
                }
                leaf-list overrides {
                    type string;
                    description "Default filters this filter replaces (e.g., rfc:no-self-as)";
                }
            }
        }
    }

    // Stage 3: Plugin declares OPEN capabilities.

    rpc declare-capabilities {
        description
            "Plugin declares capabilities for BGP OPEN injection.
             Called during Stage 3 of the 5-stage startup protocol.";
        input {
            list capability {
                key "code";
                leaf code {
                    type uint8;
                    description "BGP capability code (RFC 5492)";
                }
                leaf encoding {
                    type enumeration {
                        enum hex { description "Hex-encoded payload"; }
                        enum b64 { description "Base64-encoded payload"; }
                        enum text { description "Text payload"; }
                    }
                    default hex;
                    description "Payload encoding";
                }
                leaf payload {
                    type string;
                    description "Encoded capability value (empty for zero-length)";
                }
                leaf-list peers {
                    type string;
                    description "Peer addresses (empty = global/all peers)";
                }
            }
        }
    }

    // Stage 5: Plugin signals readiness.

    rpc ready {
        description
            "Plugin signals it is operational and ready to process events.
             Called during Stage 5 of the 5-stage startup protocol.";
    }

    // Runtime: Route injection.

    rpc update-route {
        description
            "Plugin injects a route update to matching peers.";
        input {
            leaf peer-selector {
                type string;
                default "*";
                description "Peer selector (* for all, or specific IP)";
            }
            leaf command {
                type string;
                mandatory true;
                description "Route command (e.g., announce/withdraw text)";
            }
        }
        output {
            leaf peers-affected {
                type uint32;
                description "Number of peers that received the route";
            }
            leaf routes-sent {
                type uint32;
                description "Number of routes sent";
            }
        }
    }

    // Runtime: Command dispatch (inter-plugin communication).

    rpc dispatch-command {
        description
            "Plugin dispatches a command through the engine's command dispatcher.
             Enables inter-plugin communication: the engine routes the command
             to the target plugin via longest-match registry lookup and returns
             the full {status, data} response. Unlike update-route, which
             extracts only route counters, this preserves structured responses.";
        input {
            leaf command {
                type string;
                mandatory true;
                description "Command string to dispatch (e.g., bgp rib list)";
            }
        }
        output {
            leaf status {
                type string;
                description "Response status (done or error)";
            }
            leaf data {
                type string;
                description "JSON-encoded response data from target handler";
            }
        }
    }

    // Runtime: Event subscription management.

    rpc subscribe-events {
        description
            "Request event delivery from the engine.";
        input {
            leaf-list events {
                type string;
                description "Event types (update, open, notification, keepalive, state, all)";
            }
            leaf-list peers {
                type string;
                description "Peer filter (empty = all peers)";
            }
            leaf format {
                type string;
                default "parsed";
                description "Event format (hex, base64, parsed, full)";
            }
        }
    }

    rpc unsubscribe-events {
        description "Stop event delivery.";
    }

    // Runtime: Wire decoding services.
    // Plugins call these to decode BGP wire data via the engine's parsers.

    rpc decode-nlri {
        description
            "Decode NLRI hex for a specific address family.
             Engine routes to the compile-time plugin registry for decoding.";
        input {
            leaf family {
                type string;
                mandatory true;
                description "Address family (e.g., ipv4/unicast, l2vpn/evpn)";
            }
            leaf hex {
                type string;
                mandatory true;
                description "Hex-encoded NLRI wire bytes";
            }
        }
        output {
            leaf json {
                type string;
                description "JSON-encoded decoded NLRI";
            }
        }
    }

    rpc encode-nlri {
        description
            "Encode NLRI from text arguments for a specific address family.
             Engine routes to the compile-time plugin registry for encoding.";
        input {
            leaf family {
                type string;
                mandatory true;
                description "Address family (e.g., ipv4/flow, l2vpn/evpn)";
            }
            leaf-list args {
                type string;
                description "Encoding arguments (family-specific)";
            }
        }
        output {
            leaf hex {
                type string;
                description "Hex-encoded NLRI wire bytes";
            }
        }
    }

    rpc decode-mp-reach {
        description
            "Decode a full MP_REACH_NLRI attribute value (RFC 4760 Section 3).
             Engine extracts address family, next-hop, and decoded NLRI.";
        input {
            leaf hex {
                type string;
                mandatory true;
                description "Hex-encoded MP_REACH_NLRI value (after TLV header)";
            }
            leaf add-path {
                type boolean;
                default false;
                description "Whether NLRI includes ADD-PATH path-id (RFC 7911)";
            }
        }
        output {
            leaf family {
                type string;
                description "Decoded address family (e.g., ipv4/unicast)";
            }
            leaf next-hop {
                type string;
                description "Decoded next-hop address";
            }
            leaf nlri {
                type string;
                description "JSON array of decoded NLRI entries";
            }
        }
    }

    rpc decode-mp-unreach {
        description
            "Decode a full MP_UNREACH_NLRI attribute value (RFC 4760 Section 4).
             Engine extracts address family and decoded withdrawn NLRI.";
        input {
            leaf hex {
                type string;
                mandatory true;
                description "Hex-encoded MP_UNREACH_NLRI value (after TLV header)";
            }
            leaf add-path {
                type boolean;
                default false;
                description "Whether NLRI includes ADD-PATH path-id (RFC 7911)";
            }
        }
        output {
            leaf family {
                type string;
                description "Decoded address family (e.g., ipv4/unicast)";
            }
            leaf nlri {
                type string;
                description "JSON array of decoded withdrawn NLRI entries";
            }
        }
    }

    rpc decode-update {
        description
            "Decode a full UPDATE message body (RFC 4271 Section 4.3).
             Engine parses attributes, NLRI, and withdrawn routes.
             Returns ze-bgp JSON format (same structure as deliver-event).";
        input {
            leaf hex {
                type string;
                mandatory true;
                description "Hex-encoded UPDATE body (after 19-byte BGP header)";
            }
            leaf add-path {
                type boolean;
                default false;
                description "Whether NLRI includes ADD-PATH path-id (RFC 7911)";
            }
        }
        output {
            leaf json {
                type string;
                description "ze-bgp JSON with update attributes and NLRI";
            }
        }
    }

    // Runtime: Event emission (plugin-generated events).

    rpc emit-event {
        description
            "Plugin emits a custom event to subscribers.
             The engine routes the event to all plugins subscribed to the
             matching namespace and event-type.";
        input {
            leaf namespace {
                type string;
                mandatory true;
                description "Event namespace (e.g., bgp, rib)";
            }
            leaf event-type {
                type string;
                mandatory true;
                description "Event type (e.g., rpki, update)";
            }
            leaf direction {
                type string;
                default "received";
                description "Event direction (received, sent, both)";
            }
            leaf peer-address {
                type string;
                default "*";
                description "Peer address for event routing (* for all)";
            }
            leaf event {
                type string;
                mandatory true;
                description "JSON-encoded event payload";
            }
        }
        output {
            leaf delivered {
                type uint32;
                description "Number of plugins that received the event";
            }
        }
    }

    // Error identities.

    identity registration-conflict {
        description "Family or command already claimed by another plugin";
    }

    identity stage-timeout {
        description "Barrier timeout exceeded during startup";
    }

    identity invalid-route {
        description "Route parsing failed";
    }
}
