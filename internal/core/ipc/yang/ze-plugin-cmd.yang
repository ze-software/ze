module ze-plugin-cmd {
    namespace "urn:ze:plugin:cmd";
    prefix plcmd;

    import ze-extensions { prefix ze; }

    description
        "Plugin operational command tree for Ze CLI.
         Covers plugin introspection and session lifecycle commands.";

    revision 2026-03-16 {
        description "Initial revision";
    }

    container plugin {
        config false;

        container help {
            config false;
            ze:command "ze-plugin:help";
            ze:rpc "ze-plugin-api:help";
            description "The answer is the two words session and command. It is a constant of
the daemon, so it does not grow when a plugin registers a command.";
            ze:help "List the subcommands the plugin verb accepts.";
        }

        container command {
            config false;
            description "Only the commands a plugin registered are reachable here. The daemon's
own built-in commands are answered by system command list instead.";
            ze:help "Inspect the commands the plugins registered.";

            container list {
                config false;
                ze:command "ze-plugin:command-list";
                ze:rpc "ze-plugin-api:command-list";
                description "Each row carries the command name and its summary, and nothing
else. Use plugin command help for the explanation, the argument form and the source plugin.";
                ze:help "List every command a plugin registered, with its summary.";
            }

            container help {
                config false;
                ze:command "ze-plugin:command-help";
                ze:rpc "ze-plugin-api:command-help";
                description "The name is looked up in the plugin registry only, so a built-in
command is reported as unknown. The answer carries the summary, the long explanation, the
argument form and the plugin that registered it.";
                ze:help "Show one plugin command's summary, explanation, arguments, and source plugin.";
                leaf name {
                    type string;
                    mandatory true;
                    description "The full command name, as plugin command list prints it. A name
no plugin registered fails with unknown plugin command.";
                    ze:help "Plugin command name";
                }
            }

            container complete {
                config false;
                ze:command "ze-plugin:command-complete";
                ze:rpc "ze-plugin-api:command-complete";
                description "The candidates come from the plugin registry only, and a command
marked hidden is left out. A built-in command is never offered here.";
                ze:help "List the completion candidates for a partial plugin command.";
                leaf partial {
                    type string;
                    mandatory true;
                    description "The text typed so far. The candidates match it on a
case-insensitive prefix over the plugin command names.";
                    ze:help "Partial command text";
                }
            }
        }

        container session {
            config false;
            description "The three commands are ready, ping and bye. A plugin process sends them
over the API socket as it starts, runs and stops.";
            ze:help "Drive the lifecycle of this plugin session.";

            container ready {
                config false;
                ze:command "ze-plugin:session-ready";
                ze:rpc "ze-plugin-api:session-ready";
                description "The reactor counts one signal for each configured plugin process,
and it stops waiting when the count reaches that total. A daemon that runs without a
reactor accepts the command and acts on nothing.";
                ze:help "Signal that this plugin process finished its initialization.";
            }

            container ping {
                config false;
                ze:command "ze-plugin:session-ping";
                ze:rpc "ze-plugin-api:session-ping";
                description "The answer carries the process id of the daemon process, not of the
plugin that asked. The command takes no argument and never fails.";
                ze:help "Answer a health check with the daemon process id.";
            }

            container bye {
                config false;
                ze:command "ze-plugin:session-bye";
                ze:rpc "ze-plugin-api:session-bye";
                description "The daemon answers goodbye. It holds no per-client state today, so
the command frees nothing and is a courtesy.";
                ze:help "Tell the daemon this session is disconnecting.";
            }
        }
    }
}
