module ze-plugin-api {
    namespace "urn:ze:plugin:api";
    prefix plug;

    import ze-extensions { prefix ze; }

    description
        "Plugin lifecycle API operations for Ze.
         RPCs for plugin session management and health checking.";

    // The session leaf was declared on the copy of session-peer-ready in
    // ze-bgp-cmd-peer-api.yang, which published a method no handler answers.
    revision 2026-10-08 {
        description "Declare the session token input of session-peer-ready.";
    }

    revision 2026-02-01 {
        description "Initial revision";
    }

    // Introspection

    rpc help {
        description "The answer names two subcommands, session and command. The
plugin verb accepts nothing else, so a third word is a mistake.";
        ze:help "List the subcommands the plugin verb accepts.";
        output {
            leaf-list subcommands {
                type string;
                description "The list is fixed at build time and holds the two words session
and command. It reads no registry.";
                ze:help "Available subcommands";
            }
        }
    }

    rpc command-list {
        description "The list holds what a plugin registered and it holds no
built-in command. Each entry carries a name and a description, and the
description is the one-line summary. Read the long explanation with 'plugin
command help <name>'.";
        ze:help "List every command a plugin registered, with its summary.";
        output {
            list command {
                description "The rows are read from the plugin command registry, in the order
it holds them. A daemon with no dispatcher answers an empty list.";
                ze:help "One row per plugin command.";
                leaf name {
                    type string;
                    description "The name the owning plugin declared at Stage 1, as the
dispatcher registered it.";
                    ze:help "Command name";
                }
                leaf description {
                    type string;
                    description "The one-line summary the plugin declared as its short help.
The long explanation is not in this list.";
                    ze:help "Command description";
                }
            }
        }
    }

    rpc command-help {
        description "The answer carries command, short-help, description, args and
source. The source names the plugin process that registered the command. An
unknown name fails with 'unknown plugin command: <name>'.";
        ze:help "Show one plugin command's summary, explanation, arguments, and source plugin.";
        input {
            leaf name {
                type string;
                mandatory true;
                description "The full command name, as command-list prints it. The lookup
reads the plugin registry alone, so a built-in name is unknown here.";
                ze:help "Command name";
            }
        }
        output {
            leaf help {
                type string;
                description "The answer carries the command name, its summary, its explanation,
its argument names and the process name of the plugin that owns it.";
                ze:help "Detailed help text";
            }
        }
    }

    rpc command-complete {
        description "Ze matches the partial text against the plugin command
registry only, so a built-in command never appears here. The answer carries a
completions list, and an empty list means no plugin command matched.";
        ze:help "List the completion candidates for a partial plugin command.";
        input {
            leaf partial {
                type string;
                mandatory true;
                description "The text the operator typed so far. Plugin command names that start
with it are the candidates.";
                ze:help "Partial command string";
            }
        }
        output {
            leaf-list completions {
                type string;
                description "Each entry is one candidate with its summary. The answer succeeds
with an empty list when nothing matched.";
                ze:help "Completion candidates";
            }
        }
    }

    // Session lifecycle

    rpc session-ready {
        description "The daemon then tells the BGP reactor that the API is ready,
which unblocks reactor startup. A process that serves one peer sends
session-peer-ready instead.";
        ze:help "Signal that this plugin process finished its initialization.";
    }

    rpc session-peer-ready {
        description "The daemon signals readiness for the one peer the process
serves. A plugin process sends 'session <initial-replay token>', with the token
captured from that peer's UP event, and a request from a plugin process without
the token is refused. An operator request needs no token. The reactor's refusal
of a token is answered with an error naming the peer. A request that names no
peer, or that names the wildcard peer, is accepted and signals nothing.";
        ze:help "Signal that this peer's plugin process finished its initialization.";
        input {
            leaf session {
                type string {
                    pattern '[1-9][0-9]*';
                }
                description "Opaque nonzero uint64 initial-replay token captured when this replay began.";
                ze:help "Initial-replay session token";
            }
        }
    }

    rpc session-ping {
        description "The answer carries the daemon process id under the pid key.
A caller reads that id to tell one daemon from another after a restart.";
        ze:help "Answer a health check with the daemon process id.";
        output {
            leaf pid {
                type uint32;
                description "The daemon writes its own process id here, so the value changes
when the daemon restarts. Any answer at all means the daemon is alive.";
                ze:help "Process id of the daemon that answered";
            }
        }
    }

    rpc session-bye {
        description "The daemon acknowledges the disconnect with a status of
goodbye. It frees no client state today, so a client that stops without this
call loses nothing.";
        ze:help "Tell the daemon this session is disconnecting.";
    }
}
