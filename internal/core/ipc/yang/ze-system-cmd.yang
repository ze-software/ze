module ze-system-cmd {
    namespace "urn:ze:system:cmd";
    prefix syscmd;

    import ze-extensions { prefix ze; }

    description
        "System operational command tree for Ze CLI.
         Covers system introspection and daemon lifecycle commands.";

    revision 2026-03-16 {
        description "Initial revision";
    }

    revision 2026-06-04 {
        description "Verb-first grammar: process reads under show, lifecycle actions under request.";
    }

    // System group

    container system {
        config false;
        description "The subcommands are help, dispatch, version, subsystem and command. This
container carries none of them itself, and each subcommand below reads the
daemon rather than the config.";
        ze:help "Daemon introspection and command dispatch.";

        container help {
            config false;
            ze:command "ze-plugin:system-help";
            ze:rpc "ze-system-api:help";
            description "The list carries the built-in commands first, then the commands the plugins
registered, each written as 'name - description'. A plugin command marked
hidden is left out. With no dispatcher, Ze answers a short fixed list
instead.";
            ze:help "List the subcommands the system verb accepts.";
        }

        container dispatch {
            config false;
            ze:command "ze-plugin:system-dispatch";
            ze:rpc "ze-system-api:dispatch";
            description "Ze joins the words after the keyword into one command string and runs it
through the text dispatcher the CLI uses. A plugin command is reachable this
way. With no dispatcher, the command fails with 'dispatcher not available'.";
            ze:help "Dispatch a text command through the command dispatcher.";
        }

        container version {
            config false;
            description "Two commands sit here, software and api. software answers the ze build, and
api answers the IPC protocol number. The two numbers name different things and
change at different times.";
            ze:help "Software and protocol version information.";

            container software {
                config false;
                ze:command "ze-plugin:system-version-software";
                ze:rpc "ze-system-api:version-software";
                description "The answer carries a version key and a build-date key. Both come from the
values the build stamped into the binary, so a daemon that was never rebuilt
reports the same pair after a restart.";
                ze:help "Show the ze software version.";
            }

            container api {
                config false;
                ze:command "ze-plugin:system-version-api";
                ze:rpc "ze-system-api:version-api";
                description "The answer carries one version key. It holds the IPC protocol number that the
daemon and its clients agree on, and it is not the ze software version.";
                ze:help "Show the IPC protocol version.";
            }
        }

        container subsystem {
            config false;
            description "One command sits here, list. A subsystem is a plugin process the daemon
started, and the process manager owns that set.";
            ze:help "Inspect the registered subsystems.";

            container list {
                config false;
                ze:command "ze-plugin:system-subsystem-list";
                ze:rpc "ze-system-api:subsystem-list";
                description "Each row carries the process name, its stage, a running flag and a command
count. The command count comes from the dispatcher registry, which is what
counts the commands the process actually registered.";
                ze:help "List the subsystems registered in the daemon.";
            }
        }

        container command {
            config false;
            description "Three commands sit here: list, help and complete. All three read the same
dispatcher, so a command missing from one is missing from the other two.";
            ze:help "Inspect the commands the daemon knows.";

            container list {
                config false;
                ze:command "ze-plugin:system-command-list";
                ze:rpc "ze-system-api:command-list";
                description "The rows carry the built-in commands first, then the commands the plugins
registered. Each row carries the command name, its summary and its long
explanation. Add the word verbose to put the source of each row beside it.";
                ze:help "List every command the daemon knows.";
            }

            container help {
                config false;
                ze:command "ze-plugin:system-command-help";
                ze:rpc "ze-system-api:command-help";
                description "The answer carries command, short-help, description and source. A command a
plugin registered also carries args and its timeout. An unknown name fails
with 'unknown command: <name>'.";
                ze:help "Show the detailed help for one command.";
                leaf name {
                    type string;
                    mandatory true;
                    description "The full command name, as command list prints it. A name in
neither registry fails with unknown command.";
                    ze:help "Command name";
                }
            }

            container complete {
                config false;
                ze:command "ze-plugin:system-command-complete";
                ze:rpc "ze-system-api:command-complete";
                description "Ze completes a command NAME from the partial text. Write 'args' before the
command name to complete an ARGUMENT of that command instead, in the form
'system command complete args <cmd> [<completed>...] [<partial>]'. With no partial
it lists every candidate. A builtin answers from the daemon's own state, a plugin
command from the plugin that registered it.";
                ze:help "List the completion candidates for a partial command.";
                leaf partial {
                    type string;
                    mandatory true;
                    description "The text typed so far. The candidates match it on a
case-insensitive prefix, and a prefix that matches nothing answers an empty list.";
                    ze:help "Partial command text";
                }
            }
        }
    }

    // Process status

    container show {
        config false;

        container status {
            config false;
            ze:command "ze-plugin:system-daemon-status";
            ze:rpc "ze-system-api:daemon-status";
            description "The answer carries the uptime, the peer count and the daemon start time. This
command needs a running reactor, so a daemon that has none refuses it.";
            ze:help "Show process status, uptime, and resource usage.";
        }
    }

    // Process lifecycle actions

    container request {
        config false;

        container plugin {
            config false;
            description "Actions on one plugin of the running daemon. Nothing here writes
configuration.";
            ze:help "Plugin operator actions.";

            container restart {
                config false;
                ze:command "ze-plugin:system-plugin-restart";
                description "Starts a configured plugin again. A stopped one starts: one its failure
policy left stopped, one the respawn limit disabled (the order lifts the limit),
one whose restart or startup handshake failed. A running one is stopped first,
which cuts the commands it was serving, and started again with the running
configuration; its failure policy is not applied. ze doctor names this command
as the fix of doctor-plugin-stopped and of the rows a new process clears. A name
no configuration or auto-load started is refused, and so is a restart a plugin
asks for itself (its own request would never end), a restart while a config
transaction is in flight, and a restart of a plugin whose removal by a reload
is still pending. A restart whose old process has not finished its cleanup
fails and leaves the plugin down until that cleanup ends.";
                ze:help "Restart a plugin, stopping it first if it runs.";

                leaf name {
                    type string;
                    mandatory true;
                    description "The plugin's configured name, as ze doctor and show health name it.";
                    ze:help "Name of the configured plugin to start again.";
                }
            }
        }

        container shutdown {
            config false;
            ze:command "ze-plugin:system-daemon-shutdown";
            ze:rpc "ze-system-api:daemon-shutdown";
            description "Ze writes the accepted answer first and stops after, so teardown cannot close
the requesting connection under its own reply. The answer message is 'shutdown
initiated'. A daemon with no reactor uses the same signal-based teardown that
SIGTERM triggers.";
            ze:help "Gracefully shutdown: drain connections, close peers, exit.";
        }

        container reboot {
            config false;
            ze:command "ze-plugin:system-daemon-reboot";
            ze:rpc "ze-system-api:daemon-reboot";
            description "Ze writes the accepted answer first, then runs the reboot. The answer message
is 'reboot initiated'. A daemon with no reboot function configured fails with
'reboot not available'.";
            ze:help "Gracefully shutdown then reboot the system.";
        }

        container halt {
            config false;
            ze:command "ze-plugin:system-daemon-quit";
            ze:rpc "ze-system-api:daemon-quit";
            description "Ze writes every goroutine stack through the daemon logger at warning
level, with a 1 MB buffer, and then stops the way 'request shutdown' does,
stop drain included. Use it where a daemon is stuck and the stacks are the
evidence.";
            ze:help "Dump goroutine stacks to stderr, then shut down as 'request shutdown' does.";
        }

        container reload {
            config false;
            ze:command "ze-plugin:system-daemon-reload";
            ze:rpc "ze-system-api:daemon-reload";
            description "Ze reads the config from disk, verifies it with every plugin that asked for
the config roots, and then applies it to each. Every plugin verifies before
any plugin applies. A failure at any step answers 'reload failed:
<error>'.";
            ze:help "Reload the configuration without restarting.";
        }

        container quiesce {
            config false;
            ze:command "ze-plugin:system-quiesce";
            ze:rpc "ze-system-api:quiesce";
            description "It is a test and operator barrier that replaces a fixed sleep.";
            ze:help "Block until every subsystem has drained pending async work, then reply.";
        }
    }
}
