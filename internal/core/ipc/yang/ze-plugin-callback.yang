module ze-plugin-callback {
    namespace "urn:ze:plugin:callback";
    prefix callback;

    import ze-extensions { prefix ze; }
    import ze-types { prefix zt; }

    description
        "RPCs served by the plugin for the engine to call (Socket B).
         The engine uses these RPCs during startup to deliver config and
         registry, and at runtime to deliver events and request encoding.";

    revision 2026-02-01 {
        description "Initial revision";
    }

    grouping source-policy-receipt {
        description "Exact identity shared by a source-policy request and its receipt.";
        leaf transaction-id {
            type string { length "1..256"; }
            mandatory true;
            ze:help "Original transaction identity";
            description "Must match the retained transaction.";
        }
        leaf operation {
            type enumeration {
                enum prepare { ze:help "Pin original source state"; }
                enum apply { ze:help "Invalidate source eligibility"; }
                enum abort { ze:help "Restore pinned source state"; }
                enum finalize { ze:help "Release accepted transaction pins"; }
            }
            mandatory true;
            ze:help "Source-policy lifecycle operation";
            description "Unknown or absent operations are refused.";
        }
        container source {
            description "Captured original source identity, never a successor.";
            ze:help "Captured source identity";
            leaf peer {
                type string { length "1..256"; }
                mandatory true;
                ze:help "Source peer identity";
                description "The source peer selected by the coordinator.";
            }
            leaf peer-owner {
                type uint64 { range "1..max"; }
                mandatory true;
                ze:help "Peer incarnation";
                description "Stable across reconnects of this peer object.";
            }
            leaf session-generation {
                type uint64 { range "1..max"; }
                mandatory true;
                ze:help "Captured session generation";
                description "Independent of the source policy epoch.";
            }
            leaf policy-epoch {
                type uint64 { range "1..max"; }
                mandatory true;
                ze:help "Original source policy epoch";
                description "The epoch pinned at prepare.";
            }
            leaf receive-frontier {
                type uint64;
                mandatory true;
                ze:help "Receive publication frontier";
                description "Explicit zero is valid; absent or null is malformed.";
            }
            leaf template-generation {
                type uint64;
                mandatory true;
                ze:help "Captured template generation";
                description "Explicit zero is valid for a source without a dynamic template.";
            }
        }
        leaf next-policy-epoch {
            type uint64;
            mandatory true;
            ze:help "Target policy epoch";
            description "Apply requires a fresh epoch newer than the original. Abort carries explicit zero for a transaction that was prepared and never applied (the owner only releases its pins), or a fresh epoch newer than the original after apply. Prepare and finalize require explicit zero.";
        }
    }

    rpc source-policy {
        ze:method "ze-plugin-callback:source-policy";
        ze:help "Settle a captured source-policy lifecycle operation.";
        description "Prepare follows strict event application drain. The owner fences asynchronous work and downstream settlement before returning. It retains pins until abort or finalize; this is not shutdown drain.";
        input {
            uses source-policy-receipt;
            leaf deadline-ms {
                type int64 { range "1..max"; }
                mandatory true;
                ze:help "Absolute operation deadline in Unix milliseconds";
                description "Expired requests never invoke the handler; all owner work must honor this bound.";
            }
        }
        output {
            uses source-policy-receipt;
            leaf status {
                type enumeration {
                    enum ok { ze:help "Owner work settled"; }
                    enum error { ze:help "Owner work failed"; }
                }
                mandatory true;
                ze:help "Actual operation outcome";
                description "Only ok acknowledges completed work for the exact echoed identity.";
            }
            leaf error {
                type string { length "0..4096"; }
                ze:help "Owner failure";
                description "Explains failed application or settlement; absent on success.";
            }
        }
    }

    rpc config-complete {
        ze:method "ze-plugin-callback:config-complete";
        ze:help "Complete retained config undo after whole-reload acceptance or abort.";
        description "An acknowledged completion for the captured plugin lifetime. Accepted follows irreversible publication; rejection follows original operation undo and old configuration restoration. A receipt means cleanup finished, not queued.";
        input {
            leaf transaction-id {
                type string { length "1..256"; }
                mandatory true;
                ze:help "Original transaction identity";
                description "Must match retained work; never selects a newer transaction.";
            }
            leaf accepted {
                type boolean;
                mandatory true;
                ze:help "Whether publication is irreversible";
                description "True releases undo without rollback; false completes a restored transaction.";
            }
            leaf deadline-ms {
                type int64 { range "1..max"; }
                mandatory true;
                ze:help "Absolute completion deadline in Unix milliseconds";
                description "The handler must finish cleanup within this deadline.";
            }
        }
        output {
            leaf transaction-id {
                type string { length "1..256"; }
                mandatory true;
                ze:help "Completed transaction identity";
                description "Echoes the request identity; mismatched receipts are refused.";
            }
            leaf accepted {
                type boolean;
                mandatory true;
                ze:help "Completed decision";
                description "Echoes the request decision.";
            }
            leaf status {
                type enumeration {
                    enum ok { ze:help "Cleanup completed"; }
                    enum error { ze:help "Cleanup failed"; }
                }
                mandatory true;
                ze:help "Actual completion outcome";
                description "Only ok acknowledges completed cleanup.";
            }
            leaf error {
                type string { length "0..4096"; }
                ze:help "Cleanup failure";
                description "Names the failed owner operation without claiming rollback after acceptance.";
            }
        }
    }

    // Stage 2: Engine delivers configuration.

    rpc configure {
        ze:method "ze-plugin-callback:configure";
        description "Called during Stage 2 of the 5-stage startup protocol.";
        ze:help "Engine delivers configuration sections to the plugin.";
        input {
            list section {
                key "root";
                description
                    "The list holds one entry for each root the plugin asked for that has
                     config, in the order the plugin named them. A plugin that asked for
                     nothing receives an empty list and the claims beside it.";
                ze:help "Config subtrees the plugin asked for at Stage 1.";
                leaf root {
                    type string;
                    description
                        "One section arrives for each root the plugin named in wants-config at
                         Stage 1, and a root with no config is left out. The value repeats the
                         name the plugin asked for.";
                    ze:help "Config root name (e.g., bgp, environment)";
                }
                leaf data {
                    type string;
                    description
                        "The subtree is wrapped in its full path from the root, so a plugin that
                         asked for bgp reads an object with one bgp key. The order of a
                         reordered list travels inside it.";
                    ze:help "JSON-encoded config data for this root";
                }
            }
        }
    }

    // Stage 4: Engine shares command registry.

    rpc share-registry {
        ze:method "ze-plugin-callback:share-registry";
        description "Called during Stage 4 of the 5-stage startup protocol.";
        ze:help "Engine shares the full command registry with the plugin.";
        input {
            list command {
                key "name";
                description
                    "The engine builds the list from the plugin registry after every plugin
                     registered, so it is complete at Stage 4. A plugin reads it to learn which
                     commands dispatch-command can reach.";
                ze:help "Every command any plugin registered.";
                leaf name {
                    type string;
                    description
                        "The name is the one the owning plugin declared at Stage 1. The list
                         holds every plugin's commands, this plugin's own included.";
                    ze:help "Command name";
                }
                leaf plugin {
                    type string;
                    description
                        "The process name of the plugin that declared the command. A plugin
                         reads it to learn which peer process answers a dispatch.";
                    ze:help "Plugin that registered this command";
                }
                leaf encoding {
                    type string;
                    description
                        "The value is copied from the registry row and is absent when the owning
                         plugin declared none.";
                    ze:help "Command encoding (text, hex, b64)";
                }
            }
        }
    }

    // Runtime: Event delivery.

    rpc deliver-event {
        ze:method "ze-plugin-callback:deliver-event";
        description "Timeout on delivery is FATAL (program terminates).";
        ze:help "Engine delivers a BGP event to the plugin.";
        input {
            leaf event {
                type string;
                mandatory true;
                description
                    "The body is built in the format the plugin asked for in subscribe-events:
                     hex, base64, parsed or full. A plugin that asked for an envelope reads
                     the namespace and event name around the payload.";
                ze:help "JSON-encoded BGP event";
            }
        }
    }

    // Runtime: NLRI encoding/decoding callbacks.

    rpc encode-nlri {
        ze:method "ze-plugin-callback:encode-nlri";
        description "The plugin answers one hex string, which the engine writes to the wire as
the NLRI body. A plugin that registers no OnEncodeNLRI handler cannot answer,
so the family it claims stays unencodable and the engine has nothing to send.";
        ze:help "Engine requests NLRI encoding from the plugin.";
        input {
            leaf family {
                type string;
                mandatory true;
                description
                    "The form is afi/safi, and it is one of the families the plugin declared
                     with mode encode or both. The engine calls the plugin that registered
                     that family.";
                ze:help "Address family (e.g., ipv4/flow, l2vpn/evpn)";
            }
            leaf-list args {
                type string;
                description
                    "The words are the operator's text after the family name, in order. The
                     plugin defines their form, and the engine passes them without reading
                     them.";
                ze:help "Encoding arguments";
            }
        }
        output {
            leaf hex {
                type string;
                description
                    "The text is the NLRI body as hex with no separator. The engine decodes it
                     and writes the bytes into the UPDATE.";
                ze:help "Hex-encoded NLRI wire bytes";
            }
        }
    }

    rpc decode-nlri {
        ze:method "ze-plugin-callback:decode-nlri";
        description "The plugin answers a value, and the SDK marshals it ONCE into the json
field rather than encoding a string that holds encoded JSON. This is the
receive direction of encode-nlri, and a plugin that claims a family declares
both or the family works in one direction only.";
        ze:help "Engine requests NLRI decoding from the plugin.";
        input {
            leaf family {
                type string;
                mandatory true;
                description
                    "The form is afi/safi, and it is one of the families the plugin declared
                     with mode decode or both.";
                ze:help "Address family";
            }
            leaf hex {
                type string;
                mandatory true;
                description
                    "The text is the NLRI field alone, as hex with no separator. The
                     MP_REACH_NLRI header is already removed.";
                ze:help "Hex-encoded NLRI wire bytes";
            }
            leaf add-path {
                type boolean;
                default false;
                description
                    "The session negotiated a four-octet Path Identifier before each NLRI,
                     including identifiers of zero. The bytes alone do not specify framing.";
                ze:help "NLRI carries negotiated ADD-PATH identifiers";
            }
            leaf withdraw {
                type boolean;
                default false;
                description
                    "True selects MP_UNREACH withdrawal semantics. False or absent selects
                     announcement semantics. The caller supplies the enclosing message's
                     action; a decoder must not infer it from the NLRI bytes.";
                ze:help "Decode NLRI with withdrawal semantics";
            }
        }
        output {
            leaf json {
                type string;
                description
                    "The value is the plugin's decoded NLRI as one JSON document. The engine
                     places it in the event it delivers to subscribers.";
                ze:help "JSON-encoded decoded NLRI";
            }
        }
    }

    rpc decode-capability {
        ze:method "ze-plugin-callback:decode-capability";
        description "The engine passes the numeric capability code and the option bytes as hex,
so a plugin decodes a code the engine itself does not know. The answer is
marshaled once into the json field, the shape decode-nlri also uses.";
        ze:help "Engine requests capability decoding from the plugin.";
        input {
            leaf code {
                type uint8;
                mandatory true;
                description
                    "The value is the capability code from the OPEN message, in the range 0 to
                     255 of RFC 5492.";
                ze:help "BGP capability code";
            }
            leaf hex {
                type string;
                mandatory true;
                description
                    "The text is the capability value alone, as hex with no separator. The code
                     and length bytes are already removed.";
                ze:help "Hex-encoded capability bytes";
            }
        }
        output {
            leaf json {
                type string;
                description
                    "The value is the plugin's decoded capability as one JSON document.";
                ze:help "JSON-encoded decoded capability";
            }
        }
    }

    // Runtime: Command execution.

    rpc execute-command {
        ze:method "ze-plugin-callback:execute-command";
        description "The serial correlates the answer with this request. The engine can have
several requests in flight on one connection. A handler CAN answer with
records, which is a walk and not a built value. Over the socket that arrives
as a head, its records and a terminator. Over the direct bridge it collapses
to the single document the record path would have carried.";
        ze:help "Engine requests the plugin to execute a command.";
        input {
            leaf serial {
                type string;
                mandatory true;
                description
                    "The engine sets it, and the plugin copies it into its answer unchanged.
                     Two requests in flight on one connection never share a serial.";
                ze:help "Correlation serial for response tracking";
            }
            leaf command {
                type string;
                mandatory true;
                description
                    "The name is one the plugin declared at Stage 1, and the engine sends the
                     declared name rather than the text the operator typed.";
                ze:help "Command to execute";
            }
            leaf-list args {
                type string;
                description
                    "The words are the operator's arguments after the command name, in order.
                     On a completion request they are the arguments already completed.";
                ze:help "Command arguments";
            }
            leaf peer {
                type string;
                description
                    "The value is the peer selector the command was reached under, and it is
                     absent when there was none. On a completion request the engine puts the
                     partial word here instead.";
                ze:help "Peer context for the command";
            }
        }
        output {
            leaf status {
                type enumeration {
                    enum done { ze:help "Command completed successfully"; }
                    enum error { ze:help "Command failed"; }
                }
                description
                    "The engine reads error as a failed command and reports the data field
                     as its message. Any other value is passed through as the response status.";
                ze:help "Execution result status";
            }
            leaf data {
                type string;
                description
                    "On done, the bytes are the answer the engine passes to the operator without
                     decoding them. On error, the text is the message the operator reads.";
                ze:help "JSON result data or error message";
            }
        }
    }

    // Runtime: Route filter callback.

    rpc filter-update {
        ze:method "ze-plugin-callback:filter-update";
        description
            "The engine sends the routes queued for the plugin when the exchange starts,
             at most 64 (FilterUpdateBatchMax), and the plugin answers one verdict per
             route in request order, all within one 5 second timeout.";
        ze:help "Engine sends UPDATE attributes to a named filter plugin.";
        input {
            list routes {
                description
                    "One entry per route of the exchange, in the order the engine queued them:
                     routes from one source keep the order that source produced them.";
                ze:help "The routes of one exchange";
                leaf filter {
                    type string;
                    mandatory true;
                    description
                        "The name is the one the peer's filter block references, without the
                         plugin prefix. The engine reads the on-error policy and the declared reads from
                         the declaration of this name, or from a name-pattern it matches when none does.";
                    ze:help "Filter name (declared at stage 1)";
                }
                leaf direction {
                    type string;
                    mandatory true;
                    description
                        "The value is import for an UPDATE the peer sent and export for one Ze is
                         about to send. A teardown answer is honored on import alone.";
                    ze:help "import or export";
                }
                leaf peer {
                    type string;
                    mandatory true;
                    description
                        "The address of the peer the UPDATE was received from, or the peer it is
                         about to be sent to.";
                    ze:help "Peer IP address";
                }
                leaf peer-as {
                    type uint32;
                    mandatory true;
                    description
                        "The value is the AS number of that same peer, as a plain number.";
                    ze:help "Peer ASN";
                }
                leaf update {
                    type string;
                    mandatory true;
                    description
                        "The text is the chain's running result, so a modify an earlier filter
                         answered is already applied when this filter reads it. A modify this filter
                         answers is applied before the next filter runs. A chain that also holds
                         in-process filters sends the empty string: its filters read fields.";
                    ze:help "Text-format attributes and NLRI (only declared attributes; empty in a mixed chain)";
                }
                anyxml fields {
                    description
                        "A JSON object holding the route fields the filter declared it reads, keyed
                         by vocabulary field name, each value in the shape the UPDATE event's attr map
                         uses. A declared field the route does not carry is left out, and the member
                         is absent when the filter declared no route field. In a chain of plugin
                         filters alone, the values are the route as the chain received it: a modify
                         an earlier filter answered reaches this filter in update alone. In a chain
                         that also holds in-process filters, the values are the route as the earlier
                         members left it, their sets applied.";
                    ze:help "Declared route fields keyed by field name (JSON object)";
                }
                leaf raw {
                    type string;
                    description
                        "The bytes are the UPDATE body after the 19-byte header, base64 encoded
                         because the field is bytes on the wire. It is present when the filter
                         declared the raw entry in its reads and the engine holds the body.";
                    ze:help "Base64-encoded raw UPDATE body (if the filter's reads hold raw)";
                }
            }
        }
        output {
            list verdicts {
                description
                    "One entry per route, in request order. A reply with more or fewer
                     verdicts than routes is malformed: none is applied, and every route of the
                     batch takes the filter's on-error.";
                ze:help "One verdict per route, in request order";
                leaf action {
                    type enumeration {
                        enum accept { ze:help "Pass update unchanged"; }
                        enum reject { ze:help "Drop update, short-circuit chain"; }
                        enum modify { ze:help "Apply delta changes"; }
                        enum withdraw { ze:help "Remove the route: withdrawn on import, withdrawn toward the peer on export"; }
                    }
                    mandatory true;
                    description
                        "A withdraw removes the route rather than only stopping it: on import the
                         route is treated as withdrawn by the peer that sent it, on export it is
                         withdrawn toward the destination. It is answered by a filter the policy
                         chain runs as a member; a text-mode filter answering it fails under its
                         on-error. A value outside the four is read as reject, and the chain
                         records that the filter failed rather than decided.";
                    ze:help "Filter decision";
                }
                leaf update {
                    type string;
                    description
                        "The text names the attributes to change and nothing else. The engine
                         rejects the route when the delta touches an attribute the filter did not
                         declare.";
                    ze:help "Delta-only modified attributes (action=modify)";
                }
                leaf raw {
                    type string;
                    description
                        "The bytes replace the whole UPDATE body, base64 encoded like the input
                         field. The engine reads it on a modify answer alone.";
                    ze:help "Base64-encoded full raw UPDATE body replacement (action=modify with raw)";
                }
                list sets {
                    description
                        "Read on action=modify for a filter in a chain that also holds in-process
                         members. A set of a field the filter did not declare in its sets, an action
                         the field does not take, or a value of the wrong shape fails the route under
                         the filter's on-error, and none of the route's sets apply.";
                    ze:help "Route fields the filter changes (action=modify)";
                    leaf field {
                        type string;
                        mandatory true;
                        ze:help "Vocabulary field name (local-preference, med, community, as-path, prefix, family)";
                    }
                    leaf action {
                        type enumeration {
                            enum set { ze:help "Replace the value"; }
                            enum increment { ze:help "Add to the current value"; }
                            enum decrement { ze:help "Subtract from the current value"; }
                            enum add { ze:help "Add one value to a list field"; }
                            enum remove { ze:help "Remove one value: a community, private AS numbers, a prefix, a family"; }
                            enum prepend { ze:help "Prepend local AS copies to the AS path"; }
                        }
                        mandatory true;
                        ze:help "How the field changes";
                    }
                    anyxml value {
                        ze:help "The value in the field's shape: a number, a community, a mode, a prefix or a family";
                    }
                }
                leaf error {
                    type string;
                    description
                        "Set when the filter could not judge this route: the engine applies the
                         filter's on-error to this route alone and reads nothing else of the
                         verdict.";
                    ze:help "Why the filter could not judge the route";
                }
            }
        }
    }

    // Shutdown: Clean termination.

    rpc bye {
        ze:method "ze-plugin-callback:bye";
        description "Plugin should respond, then cleanup and exit with code 0.";
        ze:help "Engine requests the plugin to shut down cleanly.";
        input {
            leaf reason {
                type string;
                description
                    "The SDK hands the text to the plugin's bye handler. A plugin reads it to
                     tell a daemon stop from a restart, and nothing else reads it.";
                ze:help "Shutdown reason (e.g., shutdown, restart)";
            }
        }
    }

    // Error identities.

    identity configuration-failed {
        description "Configuration parsing or application failed";
    }

    identity encode-error {
        description "NLRI encoding failed";
    }

    identity decode-error {
        description "NLRI or capability decoding failed";
    }

    identity command-error {
        description "Command execution failed";
    }
}
