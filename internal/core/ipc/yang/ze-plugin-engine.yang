module ze-plugin-engine {
    namespace "urn:ze:plugin:engine";
    prefix engine;

    import ze-extensions { prefix ze; }
    import ze-types { prefix zt; }

    description
        "RPCs served by the engine for plugins to call (Socket A).
         Plugins use these RPCs during startup and runtime to register,
         declare capabilities, signal readiness, and inject routes.";

    revision 2026-02-01 {
        description "Initial revision";
    }

    grouping state-key {
        leaf key {
            type string { length "1..512"; pattern 'meta/[A-Za-z0-9_.:/-]+'; }
            mandatory true;
            ze:help "Registered state key or prefix owned by this plugin";
            description "The daemon checks the plugin's compiled key grants before accessing this raw key.";
        }
    }
    grouping state-data {
        leaf data {
            type binary { length "0..1048576"; }
            ze:help "State value encoded as base64";
            description "Raw state bytes bounded to one MiB. An empty value is valid.";
        }
    }
    grouping state-result {
        leaf status {
            type enumeration {
                enum ok { ze:help "Operation completed"; }
                enum absent { ze:help "No value is stored"; }
                enum unavailable { ze:help "Daemon has no persistent store"; }
                enum corrupt { ze:help "Stored state failed integrity checks"; }
                enum read-failed { ze:help "Stored state could not be read"; }
                enum persist-failed { ze:help "Mutation was not durably acknowledged"; }
            }
            mandatory true;
            ze:help "Explicit persistence outcome";
            description "Only ok acknowledges a mutation. Absence is distinct from unavailable or corrupt storage.";
        }
        leaf message {
            type string { length "0..4096"; }
            ze:help "Failure detail";
            description "An unsuccessful operation explains the failure without returning the stored value.";
        }
    }

    rpc state-get {
        ze:method "ze-plugin-engine:state-get";
        ze:help "Read a registered runtime key.";
        description "Read through the daemon-owned store after the startup handshake. Both transports check plugin ownership.";
        input { uses state-key; }
        output { uses state-result; uses state-data; }
    }
    rpc state-put {
        ze:method "ze-plugin-engine:state-put";
        ze:help "Persist a registered runtime key.";
        description "Write through the daemon-owned store and acknowledge only after the durable write completes.";
        input { uses state-key; uses state-data; }
        output { uses state-result; }
    }
    rpc state-remove {
        ze:method "ze-plugin-engine:state-remove";
        ze:help "Remove a registered runtime key.";
        description "Delete an owned key after startup. An absent key is already removed; unavailable storage is an error.";
        input { uses state-key; }
        output { uses state-result; }
    }
    rpc state-list {
        ze:method "ze-plugin-engine:state-list";
        ze:help "List owned runtime keys under a prefix.";
        description "Return only matching keys granted to the calling plugin. An oversized enumeration fails without truncation.";
        input { uses state-key; }
        output {
            uses state-result;
            leaf-list keys {
                type string { length "1..512"; }
                max-elements 4096;
                ze:help "Owned keys matching the prefix";
                description "Complete enumeration of matching owned keys, including nested keys.";
            }
        }
    }
    rpc metrics-publish {
        ze:method "ze-plugin-engine:metrics-publish";
        ze:help "Publish the plugin's metric declarations and the changes since its last publish.";
        description "The plugin chooses when to send it. The engine applies declarations, then deletions, then updates, each in its own metrics registry under the declared name and shape; it answers what it refused, or unavailable when it has no registry yet and applied nothing.";
        input {
            list declare {
                max-elements 512;
                ze:help "A metric to create, or to share when the name exists with the same shape";
                leaf name { type string { length "4..128"; pattern 'ze_[a-zA-Z0-9_:]*'; } ze:help "Metric name"; }
                leaf help { type string { length "1..1024"; } ze:help "Help text"; }
                leaf kind {
                    type enumeration {
                        enum counter; enum gauge; enum histogram;
                        enum counter-vec; enum gauge-vec; enum histogram-vec;
                    }
                    ze:help "The registry method the metric stands for";
                }
                leaf-list labels { type string; max-elements 16; ze:help "Label names of a vector"; }
                leaf-list buckets { type decimal64 { fraction-digits 6; } max-elements 64; ze:help "Resolved upper bounds of a histogram"; }
            }
            list delete {
                max-elements 4096;
                ze:help "A labeled series to remove";
                leaf name { type string { length "4..128"; } ze:help "Metric name"; }
                leaf-list values { type string { length "0..256"; } max-elements 16; ze:help "Label values in declared order"; }
            }
            list update {
                max-elements 4608;
                ze:help "The change of one series since the last publish";
                leaf name { type string { length "4..128"; } ze:help "Metric name"; }
                leaf-list values { type string { length "0..256"; } max-elements 16; ze:help "Label values in declared order"; }
                leaf value { type decimal64 { fraction-digits 6; } ze:help "Counter: amount added. Gauge: current value"; }
                leaf-list counts { type uint64 { range "0..1048576"; } max-elements 65; ze:help "Histogram: observations gained per bucket, +Inf last"; }
                leaf-list sums { type decimal64 { fraction-digits 6; } max-elements 65; ze:help "Histogram: sum of those observations per bucket"; }
            }
        }
        output {
            leaf unavailable { type boolean; ze:help "The engine has no metrics registry yet; nothing was applied"; }
            list refused {
                ze:help "An item the engine did not apply";
                leaf item { type enumeration { enum declare; enum delete; enum update; } ze:help "The list the item came from"; }
                leaf name { type string; ze:help "Metric name"; }
                leaf-list values { type string; ze:help "Label values"; }
                leaf reason { type string; ze:help "Why it was refused"; }
            }
        }
    }
    rpc report-issue {
        ze:method "ze-plugin-engine:report-issue";
        ze:help "Raise or clear one problem on the daemon's report bus, under the plugin's own name.";
        description "Sent after the startup handshake. The engine names the source from the plugin's authenticated name. It refuses a code that is not a registered event code, a field past its bound, a clear of an error, and more than 60 raises from one plugin in one minute, each with an error naming the cause. A raise lands on the bus show warnings, show errors and show doctor read; a clear removes the active warning of its code and subject.";
        input {
            leaf action { type enumeration { enum raise; enum clear; } mandatory true; ze:help "Raise the problem, or clear its active warning"; }
            leaf severity { type enumeration { enum warning; enum error; } ze:help "Raise: a warning stays active until cleared, an error is an event"; }
            leaf code { type string { length "1..64"; } mandatory true; ze:help "A registered event code (ze show diagnostic describes it)"; }
            leaf subject { type string { length "1..256"; } mandatory true; ze:help "What the problem is about"; }
            leaf message { type string { length "1..1024"; } ze:help "Raise: what is wrong"; }
            leaf fix { type string { length "0..256"; } ze:help "Raise: the command that fixes the subject"; }
        }
    }
    rpc state-increment {
        ze:method "ze-plugin-engine:state-increment";
        ze:help "Atomically advance a durable uint32 counter.";
        description "Increment a big-endian counter under the store write guard. Absent counters start at one; corruption and exhaustion are refused.";
        input { uses state-key; }
        output {
            uses state-result;
            leaf value {
                type uint32 { range "1..4294967295"; }
                ze:help "Durably stored counter value";
                description "The counter after the increment. No value is returned for a failed write.";
            }
        }
    }

    // Stage 1: Plugin declares itself to the engine.

    rpc declare-registration {
        ze:method "ze-plugin-engine:declare-registration";
        description "Called during Stage 1 of the 5-stage startup protocol.";
        ze:help "Plugin declares families, commands, config wants, and YANG schema.";
        input {
            leaf protocol-version {
                type uint32 {
                    range "1..max";
                }
                mandatory true;
                description
                    "The highest plugin protocol version the plugin speaks. A declaration
                     without it is from the text era and is refused at Stage 1, naming the
                     version to declare.";
                ze:help "Highest plugin protocol version the plugin speaks";
            }
            leaf config-completion {
                type boolean;
                default false;
                ze:help "Acknowledge whole-reload undo release";
                description "Declares config-complete support. Operation journals remain reversible until the engine completes the captured transaction.";
            }
            leaf source-policy-owner {
                type boolean;
                default false;
                ze:help "Declare retained source state";
                description "Independent of handler support. A selected owner without source-policy support refuses source-policy preflight.";
            }
            leaf source-policy {
                type boolean;
                default false;
                ze:help "Declare acknowledged source-policy lifecycle support";
                description "Implements prepare, apply, abort and finalize for retained source state. The SDK OnSourcePolicy registration declares both ownership and support.";
            }
            list family {
                key "name";
                description
                    "The engine adds each family to the encode or decode registry before the
                     ready barrier. A family another plugin already claimed is a registration
                     conflict and the whole registration is refused.";
                ze:help "Address families this plugin encodes or decodes.";
                leaf name {
                    type string;
                    description
                        "The form is afi/safi, and the engine refuses a name with no slash or an
                         empty half. A family that no compiled plugin registered also needs its
                         afi and safi numbers, or the engine refuses the declaration.";
                    ze:help "Address family (e.g., ipv4/unicast, l2vpn/evpn)";
                }
                leaf mode {
                    type enumeration {
                        enum encode { ze:help "Encode text to wire"; }
                        enum decode { ze:help "Decode wire to JSON"; }
                        enum both { ze:help "Encode and decode"; }
                    }
                    description
                        "The mode decides which registry the engine adds the family to. Encode
                         puts it in the encode set, decode in the decode set, and both in each.
                         An absent mode is read as encode.";
                    ze:help "Family handling mode";
                }
            }
            list command {
                key "name";
                description
                    "Each entry becomes a row in the command registry, and the engine calls the
                     plugin over execute-command when an operator runs it. The two help texts
                     and the answer shape are validated before any row is stored.";
                ze:help "Commands this plugin answers.";
                leaf name {
                    type string;
                    description
                        "The engine registers the name in the command registry before the ready
                         barrier, so another plugin can dispatch it as soon as startup ends. A name
                         another plugin already registered is a registration conflict.";
                    ze:help "Command name";
                }
                leaf description {
                    type string;
                    description
                        "The long explanation the command's own help page prints under its summary.
                         The engine stores it beside the short help, and it refuses a text that
                         carries a control character. A plugin that sends none renders with an
                         empty explanation.";
                    ze:help "Command description";
                }
                leaf-list args {
                    type string;
                    description
                        "The names are shown after the command name in the help listing and in the
                         command-help answer. The engine reads them for display alone and does not
                         validate a call against them.";
                    ze:help "Argument names";
                }
                leaf completable {
                    type boolean;
                    default false;
                    description
                        "When true, the engine forwards an argument completion request for this
                         command to the plugin over execute-command. When false, the completion
                         answer is empty and the plugin is not asked.";
                    ze:help "Supports tab completion";
                }
            }
            leaf-list wants-config {
                type string;
                description
                    "Each entry names one top-level config root, and the engine sends that subtree
                     as one section on the Stage 2 configure callback. A root with no config is
                     skipped. The single entry * asks for the whole tree.";
                ze:help "Config roots to receive (e.g., bgp, environment, *)";
            }
            leaf-list dependencies {
                type string;
                description
                    "Plugins this plugin needs. Each must be configured, or Stage 1 is refused
                     naming it. The plugin is ordered after each one it names.";
                ze:help "Plugins this plugin needs and is ordered after";
            }
            leaf-list optional-dependencies {
                type string;
                description
                    "Plugins this plugin is ordered after when they run. Order only: an entry
                     loads nothing.";
                ze:help "Plugins this plugin is ordered after when present";
            }
            leaf-list start-after {
                type string;
                description
                    "Plugins this plugin starts after when they run, and so takes state events
                     before (state is delivered in reverse order). Order only: an entry loads
                     nothing.";
                ze:help "Plugins this plugin starts after when present";
            }
            container schema {
                description
                    "The engine registers the module in the schema registry at Stage 1. A module
                     name or a handler path another plugin already registered is refused.";
                ze:help "YANG schema declaration";
                leaf module {
                    type string;
                    description
                        "The registry is keyed by this name, and an empty name is refused. A
                         second plugin declaring the same module name is a duplicate.";
                    ze:help "YANG module name";
                }
                leaf namespace {
                    type string;
                    description
                        "The namespace statement of the declared module. The engine stores it
                         beside the module name and does not read it during registration.";
                    ze:help "YANG namespace URI";
                }
                leaf yang-text {
                    type string;
                    description
                        "The source text of the module, as the plugin ships it. The engine stores
                         it with the declaration so the schema can be parsed later.";
                    ze:help "Full YANG module text";
                }
                leaf-list handlers {
                    type string;
                    description
                        "Each path names a config subtree this plugin handles. The engine maps each
                         path to the module name, and a path another module already claimed is
                         refused.";
                    ze:help "Handler paths (e.g., bgp, bgp.peer)";
                }
            }
            list filter {
                description
                    "Config references a filter by name, in a filter block for
                     the import direction or the export direction. Each entry
                     carries exactly one of name and name-pattern.";
                ze:help
                    "Named route filters this plugin offers.";
                leaf name {
                    type string;
                    description
                        "The engine looks the name up when a peer's filter chain reaches this
                         plugin. A name declared exactly wins over a matching name-pattern.";
                    ze:help "Filter name (the part after : in <plugin>:<filter>)";
                }
                leaf name-pattern {
                    type string {
                        length "1..256";
                    }
                    description
                        "An RE2 expression that a whole filter name must match, for a plugin
                         whose filter names are made at run time (one per AS number, say).
                         Stage 1 refuses an expression that does not compile, and an entry
                         carrying both name and name-pattern, or neither.";
                    ze:help "Pattern covering the filter names this entry answers for";
                }
                leaf-list reads {
                    type string;
                    description
                        "Route fields of the policy vocabulary the filter reads; the engine
                         sends exactly these in each filter-update call, keyed by field name.
                         The read raw asks for the raw UPDATE body instead. Stage 1 refuses a
                         name the vocabulary does not hold and a field this build cannot
                         encode, and config load refuses a chain whose attachment does not
                         carry a field the filter reads.";
                    ze:help "Route fields the filter reads (raw for the UPDATE body)";
                }
                leaf-list sets {
                    type string;
                    description
                        "Route fields of the policy vocabulary the filter may set. Config load
                         refuses a chain whose attachment does not allow setting one of them.";
                    ze:help "Route fields the filter may set";
                }
                leaf direction {
                    type enumeration {
                        enum import { ze:help "Ingress filtering"; }
                        enum export { ze:help "Egress filtering"; }
                        enum both { ze:help "Ingress and egress filtering"; }
                    }
                    description
                        "The engine stores the direction with the filter declaration. The peer
                         config decides which chain calls the filter.";
                    ze:help "Which direction(s) this filter handles";
                }
                leaf readvertise {
                    type boolean;
                    default false;
                    description
                        "The export filter runs on the stale readvertise rail: when a
                         graceful-restart retention re-advertises its stale routes, the
                         destination's export chain runs only the members whose filter
                         declares readvertise, with the route's stale metadata set. Stage 1
                         refuses it on an import-only filter.";
                    ze:help "Run this export filter when stale routes are re-advertised";
                }
                leaf judges-final {
                    type boolean;
                    default false;
                    description
                        "The export filter runs once more over a body the export chain rewrote,
                         reading raw as the route the chain received and every other field from
                         the rewritten body. Its answer holds only against a member that does not
                         declare judges-final, and it MUST be safe to repeat. A raw answer is
                         refused when that body differs from the chain's input. Stage 1 refuses
                         it on an import-only filter.";
                    ze:help "Run this export filter again over a body the chain rewrote";
                }
                leaf-list attributes {
                    type string;
                    description
                        "The list bounds a modify answer. When the filter answers modify, the
                         engine rejects the route if the delta touches an attribute not named here.
                         An empty list leaves the delta unchecked.";
                    ze:help "Attribute names to receive (e.g., as-path, community)";
                }
                leaf nlri {
                    type boolean;
                    default true;
                    description
                        "The engine stores the flag with the filter declaration. An absent value
                         is read as true.";
                    ze:help "Whether to include NLRI list in filter input";
                }
                leaf on-error {
                    type enumeration {
                        enum reject { ze:help "Fail-closed: drop update on error"; }
                        enum accept { ze:help "Fail-open: pass update on error"; }
                    }
                    default reject;
                    description
                        "The policy applies when the filter-update call itself fails, not when
                         the plugin answers reject. An absent value is read as reject.";
                    ze:help "Behavior when filter IPC fails";
                }
                leaf-list overrides {
                    type string;
                    description
                        "Each entry names a default filter in the form <plugin>:<filter>. The
                         engine stores the list with the filter declaration.";
                    ze:help "Default filters this filter replaces (e.g., rfc:no-self-as)";
                }
            }
            list filter-insertion {
                description
                    "The config loader inserts the filter into the import or export list of
                     every peer whose resolved config meets the condition, ahead of the
                     operator's members, unless the operator names it there. A required
                     insertion refuses any operator reference to it.";
                ze:help "Members inserted into a peer's filter list by this plugin";
                leaf filter {
                    type string { length "1..512"; }
                    description
                        "A reference this plugin serves: <plugin>:<filter> of a filter it
                         declares, or <type>:<instance> of a filter type it owns.";
                    ze:help "Chain reference to insert";
                }
                leaf direction {
                    type enumeration {
                        enum import { ze:help "Insert into the import list"; }
                        enum export { ze:help "Insert into the export list"; }
                    }
                    description "Exactly one list; declare a second insertion for the other.";
                    ze:help "Which list receives the member";
                }
                leaf priority {
                    type uint16 { range "0..9999"; }
                    description "Inserted members run in ascending priority, ahead of the operator's.";
                    ze:help "Order among inserted members";
                }
                leaf-list config {
                    type string;
                    ordered-by user;
                    description
                        "The words of a path under a peer's resolved config entry (bgp, group
                         and peer merged). The condition holds where the path is present, or
                         where its leaf equals one of values.";
                    ze:help "Config path the condition reads";
                }
                leaf-list values {
                    type string;
                    description "When given, the leaf must equal one of them.";
                    ze:help "Leaf values that meet the condition";
                }
                list session {
                    description
                        "A session condition, in place of config: every fact listed holds for
                         the peer. A fact is a session fact some owner registered (the BGP view
                         registers ibgp, rs-client, peer-as and the other peer facts). A
                         dynamic peer is judged when its OPEN arrives.";
                    ze:help "Session facts the condition reads";
                    leaf fact {
                        type string { length "1..128"; }
                        description "The registered session fact.";
                        ze:help "Session fact name";
                    }
                    leaf-list values {
                        type string;
                        description
                            "When given, the fact's text form must equal one of them: a flag
                             reads true or false, an AS number in decimal.";
                        ze:help "Fact values that meet the condition";
                    }
                }
                leaf scope {
                    type enumeration {
                        enum any-peer {
                            ze:help "Judge the condition on any peer; insert on every export list";
                        }
                    }
                    description
                        "Absent, the condition is judged on each peer and the member lands on
                         that peer's list. any-peer, for a source-keyed procedure: while any
                         peer meets the config condition, the member lands on every peer's
                         export list. Refused on import and beside a session condition.";
                    ze:help "Whose condition places the member";
                }
                leaf required {
                    type boolean;
                    default false;
                    description "A required member refuses an operator reference: named, moved or inactive.";
                    ze:help "Whether the operator may place or deactivate it";
                }
                leaf reason {
                    type string { length "1..1024"; }
                    description "The text the refusal prints. Owed when required is true.";
                    ze:help "Why the member is required";
                }
            }
            list pipe {
                key "command name";
                description
                    "An alias is a word an operator types after the pipe
                     character, and it stands for an operator chain.";
                ze:help
                    "Pipe aliases this plugin offers for its own commands.";
                leaf command {
                    type string;
                    description
                        "The path MUST name a command in the command list of this same message.
                         The engine refuses an alias whose command the plugin did not declare.";
                    ze:help "Command path the alias sits on (one of this plugin's own declared commands)";
                }
                leaf name {
                    type string;
                    description
                        "The engine registers the word in the alias registry under this plugin's
                         name. It is removed when the plugin stops.";
                    ze:help "The word an operator types after the pipe character (kebab-case)";
                }
                leaf description {
                    type string;
                    description
                        "An alias carries this one text and no longer one. The expansion is
                         reported beside it as the whole of what the alias does.";
                    ze:help "The line completion and help show beside the name";
                }
                leaf expansion {
                    type string;
                    description
                        "The chain is written as an operator would type it after the pipe
                         character. The daemon runs it in place of the alias, and it names no
                         other alias.";
                    ze:help "The operator chain the name stands for, for example: display kind vrp-count";
                }
            }
        }
        output {
            leaf protocol-version {
                type uint32 {
                    range "1..max";
                }
                description
                    "The version both sides speak from here on: the lower of the
                     plugin's declared version and the engine's.";
                ze:help "Plugin protocol version both sides speak";
            }
            leaf plugin-name {
                type string {
                    length "1..64";
                }
                description
                    "The configured identity of this authenticated plugin process.
                     This can differ from the implementation the instance runs.
                     The SDK receives it before configuration and uses it in
                     operator recovery commands.";
                ze:help "Configured plugin instance name";
            }
        }
    }

    // Stage 3: Plugin declares OPEN capabilities.

    rpc declare-capabilities {
        ze:method "ze-plugin-engine:declare-capabilities";
        description "Called during Stage 3 of the 5-stage startup protocol.";
        ze:help "Plugin declares capabilities for BGP OPEN injection.";
        input {
            list capability {
                key "code";
                description
                    "The engine decodes every payload and checks every code for a conflict
                     before it stores any of them, so a refused batch injects nothing.";
                ze:help "Capabilities the engine adds to the OPEN it sends.";
                leaf code {
                    type uint8;
                    description
                        "The engine keys injected capabilities by this code. A code another
                         plugin already injected for the same peer, or globally, is a capability
                         conflict and the whole batch is refused.";
                    ze:help "BGP capability code (RFC 5492)";
                }
                leaf encoding {
                    type enumeration {
                        enum hex { ze:help "Hex-encoded payload"; }
                        enum b64 { ze:help "Base64-encoded payload"; }
                        enum text { ze:help "Text payload"; }
                    }
                    default hex;
                    description
                        "The engine decodes the payload with this encoding before it writes the
                         OPEN. A capability with no encoding and no payload is a flag with no
                         value. An absent encoding with a payload is refused.";
                    ze:help "Payload encoding";
                }
                leaf payload {
                    type string;
                    description
                        "The decoded bytes become the capability value in the OPEN message. Leave
                         it empty for a capability that carries no value.";
                    ze:help "Encoded capability value (empty for zero-length)";
                }
                leaf-list peers {
                    type string;
                    description
                        "With entries, the capability is stored for each listed peer address
                         alone. With none, it is stored once and applies to every peer.";
                    ze:help "Peer addresses (empty = global/all peers)";
                }
            }
        }
    }

    // Stage 5: Plugin signals readiness.

    rpc ready {
        ze:method "ze-plugin-engine:ready";
        description "Called during Stage 5 of the 5-stage startup protocol.";
        ze:help "Plugin signals it is operational and ready to process events.";
    }

    // Runtime: Route injection.

    rpc update-route {
        ze:method "ze-plugin-engine:update-route";
        description
            "The answer carries the announced and withdrawn NLRI counts and nothing
else. A plugin that needs the target handler's structured response calls
dispatch-command instead, which preserves it. The peer selector defaults to
every peer, so an omitted selector is not a no-op.";
        ze:help "Plugin injects a route update to matching peers.";
        input {
            leaf peer-selector {
                type string;
                default "*";
                description
                    "The engine places the selector after send bgp when it builds the command
                     it dispatches. An empty value is read as *.";
                ze:help "Peer selector (* for all, or specific IP)";
            }
            leaf command {
                type string;
                mandatory true;
                description
                    "The text is appended to send bgp <selector> and dispatched as one command.
                     It is the part after the selector, for example update text announce ....";
                ze:help "Route command (e.g., announce/withdraw text)";
            }
            leaf source-policy-epoch {
                type uint64;
                description
                    "Original admission epoch of retained received routes. Zero means
                     unrecorded provenance, never the source's current epoch.
                     This typed provenance is independent of user route metadata.";
                ze:help "Original received source policy epoch";
            }
        }
        output {
            leaf announced {
                type uint32;
                description
                    "The count is read from the route result the dispatched command produced.
                     A command the dispatcher silenced answers zero.";
                ze:help "Number of NLRIs announced";
            }
            leaf withdrawn {
                type uint32;
                description
                    "The count is read from the same route result as announced. A command the
                     dispatcher silenced answers zero.";
                ze:help "Number of NLRIs withdrawn";
            }
        }
    }

    rpc route-metrics {
        ze:method "ze-plugin-engine:route-metrics";
        ze:help "Read recursive next-hop metrics from the engine.";
        description
            "Returns the Loc-RIB revision and one result per requested address, in
             request order. An empty address list requests the revision alone.";
        input {
            leaf-list addresses {
                type zt:ip-address;
                max-elements 4096;
                ordered-by user;
                ze:help "Next-hop addresses to resolve";
                description "Each address is resolved through the engine's current Loc-RIB.";
            }
        }
        output {
            leaf revision {
                type uint64;
                mandatory true;
                ze:help "Routing revision before resolution";
                description "A later revision invalidates distances from this snapshot.";
            }
            list distances {
                max-elements 4096;
                ordered-by user;
                ze:help "Distances in the requested address order";
                description "Every requested address has one result, including unresolved addresses.";
                leaf cost {
                    type uint64;
                    mandatory true;
                    ze:help "Accumulated interior metric";
                    description "Resolved cost includes recursive BGP AIGP and terminal interior distance.";
                }
                leaf resolved {
                    type boolean;
                    mandatory true;
                    ze:help "Whether the next hop resolves";
                    description "False distinguishes an unresolved next hop from a resolved zero cost.";
                }
                leaf recursive {
                    type boolean;
                    mandatory true;
                    ze:help "Whether resolution followed a recursive next hop";
                    description "A resolved recursive sum may legitimately be zero, unlike a required direct-link AIGP increment.";
                }
                leaf missing-aigp {
                    type boolean;
                    mandatory true;
                    ze:help "Whether a recursive BGP hop omitted AIGP";
                    description "A missing AIGP attribute prevents accumulating it for next-hop-self export.";
                }
            }
        }
    }

    // Runtime: Command dispatch (inter-plugin communication).

    rpc dispatch-command {
        ze:method "ze-plugin-engine:dispatch-command";
        description "Enables inter-plugin communication: the engine routes the command
to the target plugin via longest-match registry lookup and returns
the full {status, data} response. Unlike update-route, which
extracts only route counters, this preserves structured responses.";
        ze:help "Plugin dispatches a command through the engine's command dispatcher.";
        input {
            leaf command {
                type string;
                mandatory true;
                description
                    "The engine gives the text to the same dispatcher the CLI uses, under the
                     calling plugin's internal identity. It is not prefixed, so the plugin
                     writes the whole command.";
                ze:help "Command string to dispatch (e.g., bgp rib list)";
            }
        }
        output {
            leaf status {
                type string;
                description
                    "The value is done when the target handler answered, warning when it
                     answered and stated a warning, and error when it failed. On error, the
                     error field carries the message.";
                ze:help "Response status (done, warning or error)";
            }
            leaf data {
                type string;
                description
                    "The bytes are the handler's response as it produced them, decoded once by
                     the caller. A handler that answered with records is collapsed into one
                     document here.";
                ze:help "JSON-encoded response data from target handler";
            }
            leaf-list warnings {
                type string;
                description
                    "Each entry is one line the command stated about the answer it still gave,
                     without the newline, set only when status is warning. They are the text
                     the operator's own surface prints beside the same answer. On the socket
                     they ride in the warning terminator's message field as a JSON array.";
                ze:help "Warning lines the command stated about its answer";
            }
        }
    }

    // Runtime: Event subscription management.

    rpc subscribe-events {
        ze:method "ze-plugin-engine:subscribe-events";
        description
            "An empty peer list means every peer rather than none. The format decides how
much of each message the engine builds. Hex and base64 carry the bytes. Parsed
carries the decoded message, and full carries both. A plugin that asks for
parsed pays the decode cost on every event.";
        ze:help "Request event delivery from the engine.";
        input {
            leaf-list events {
                type string;
                description
                    "Each entry is an event type, with an optional direction suffix in the form
                     update direction sent. Without the suffix, both directions match. The entry
                     * expands to every event type of the namespace at registration time.";
                ze:help "Event types (update, open, notification, keepalive, state, all)";
            }
            leaf-list peers {
                type string;
                description
                    "The engine reads the first entry alone as the peer selector for every
                     subscription in this call. An empty list matches every peer.";
                ze:help "Peer filter (empty = all peers)";
            }
            leaf format {
                type string;
                default "parsed";
                description
                    "The format is stored on the process, not on one subscription, so the last
                     subscribe call decides it for every event the process receives. An empty
                     value leaves the stored format unchanged.";
                ze:help "Event format (hex, base64, parsed, full)";
            }
        }
    }

    rpc unsubscribe-events {
        ze:method "ze-plugin-engine:unsubscribe-events";
        description "It cancels the whole subscription subscribe-events created. There is no
per-event and no per-peer form, so a plugin that wants a narrower set
unsubscribes and subscribes again with the set it wants.";
        ze:help "Stop event delivery.";
    }

    // Runtime: Wire decoding services.
    // Plugins call these to decode BGP wire data via the engine's parsers.

    rpc decode-nlri {
        ze:method "ze-plugin-engine:decode-nlri";
        description "Engine routes to the compile-time plugin registry for decoding.";
        ze:help "Decode NLRI hex for a specific address family.";
        input {
            leaf family {
                type string;
                mandatory true;
                description
                    "The form is afi/safi. The engine looks the name up in the family registry
                     to find the decoder, and a family with no registered decoder fails.";
                ze:help "Address family (e.g., ipv4/unicast, l2vpn/evpn)";
            }
            leaf hex {
                type string;
                mandatory true;
                description
                    "The bytes are the NLRI field alone, without the MP_REACH_NLRI header.
                     Text that is not valid hex fails before the decoder runs.";
                ze:help "Hex-encoded NLRI wire bytes";
            }
            leaf add-path {
                type boolean;
                default false;
                description
                    "The session negotiated a four-octet Path Identifier before each NLRI,
                     including identifiers of zero. The bytes alone do not specify framing.";
                ze:help "NLRI carries negotiated ADD-PATH identifiers";
            }
            leaf withdraw {
                type boolean;
                default false;
                description
                    "True selects MP_UNREACH withdrawal semantics. False or absent selects
                     announcement semantics. The caller supplies the enclosing message's
                     action; a decoder must not infer it from the NLRI bytes.";
                ze:help "Decode NLRI with withdrawal semantics";
            }
        }
        output {
            leaf json {
                type string;
                description
                    "The value is the JSON the family decoder produced, passed through without a
                     second encoding.";
                ze:help "JSON-encoded decoded NLRI";
            }
        }
    }

    rpc encode-nlri {
        ze:method "ze-plugin-engine:encode-nlri";
        description "Engine routes to the compile-time plugin registry for encoding.";
        ze:help "Encode NLRI from text arguments for a specific address family.";
        input {
            leaf family {
                type string;
                mandatory true;
                description
                    "The form is afi/safi. The engine looks the name up in the family registry
                     to find the encoder, and a family with no registered encoder fails.";
                ze:help "Address family (e.g., ipv4/flow, l2vpn/evpn)";
            }
            leaf-list args {
                type string;
                description
                    "The words are given to the family encoder in order. Each family defines
                     its own argument form, and the engine does not read them.";
                ze:help "Encoding arguments (family-specific)";
            }
        }
        output {
            leaf hex {
                type string;
                description
                    "The value is the wire form the family encoder produced, as hex text with
                     no separator.";
                ze:help "Hex-encoded NLRI wire bytes";
            }
        }
    }

    rpc decode-mp-reach {
        ze:method "ze-plugin-engine:decode-mp-reach";
        description "Engine extracts address family, next-hop, and decoded NLRI.";
        ze:help "Decode a full MP_REACH_NLRI attribute value (RFC 4760 Section 3).";
        input {
            leaf hex {
                type string;
                mandatory true;
                description
                    "The bytes start at the AFI field: AFI, SAFI, next-hop length, next-hop,
                     reserved byte, then NLRI. Fewer than 5 bytes is refused.";
                ze:help "Hex-encoded MP_REACH_NLRI value (after TLV header)";
            }
            leaf add-path {
                type boolean;
                default false;
                description
                    "When true, the decoder reads a 4-byte path identifier before each NLRI
                     entry. Set it to match what the session negotiated, because the engine
                     cannot tell from the bytes.";
                ze:help "Whether NLRI includes ADD-PATH path-id (RFC 7911)";
            }
        }
        output {
            leaf family {
                type string;
                description
                    "The name is derived from the AFI and SAFI fields in the form afi/safi.";
                ze:help "Decoded address family (e.g., ipv4/unicast)";
            }
            leaf next-hop {
                type string;
                description
                    "The address is read from the next-hop field. It is absent when the field
                     holds no valid address.";
                ze:help "Decoded next-hop address";
            }
            leaf nlri {
                type string;
                description
                    "Each entry is one NLRI decoded by the family decoder. A family with no
                     decoder fails the whole call.";
                ze:help "JSON array of decoded NLRI entries";
            }
        }
    }

    rpc decode-mp-unreach {
        ze:method "ze-plugin-engine:decode-mp-unreach";
        description "Engine extracts address family and decoded withdrawn NLRI.";
        ze:help "Decode a full MP_UNREACH_NLRI attribute value (RFC 4760 Section 4).";
        input {
            leaf hex {
                type string;
                mandatory true;
                description
                    "The bytes start at the AFI field: AFI, SAFI, then the withdrawn NLRI.
                     There is no next-hop in this attribute.";
                ze:help "Hex-encoded MP_UNREACH_NLRI value (after TLV header)";
            }
            leaf add-path {
                type boolean;
                default false;
                description
                    "When true, the decoder reads a 4-byte path identifier before each
                     withdrawn entry. Set it to match what the session negotiated.";
                ze:help "Whether NLRI includes ADD-PATH path-id (RFC 7911)";
            }
        }
        output {
            leaf family {
                type string;
                description
                    "The name is derived from the AFI and SAFI fields in the form afi/safi.";
                ze:help "Decoded address family (e.g., ipv4/unicast)";
            }
            leaf nlri {
                type string;
                description
                    "Each entry is one withdrawn NLRI decoded by the family decoder. A family
                     with no decoder fails the whole call.";
                ze:help "JSON array of decoded withdrawn NLRI entries";
            }
        }
    }

    rpc decode-update {
        ze:method "ze-plugin-engine:decode-update";
        description "Engine parses attributes, NLRI, and withdrawn routes.
Returns ze-bgp JSON format (same structure as deliver-event).";
        ze:help "Decode a full UPDATE message body (RFC 4271 Section 4.3).";
        input {
            leaf hex {
                type string;
                mandatory true;
                description
                    "The bytes start at the withdrawn routes length field. Fewer than 4 bytes
                     is refused. The decode uses no session state, so a 4-byte AS number is
                     read where the message carries one.";
                ze:help "Hex-encoded UPDATE body (after 19-byte BGP header)";
            }
            leaf add-path {
                type boolean;
                default false;
                description
                    "When true, the formatter reads a 4-byte path identifier before each NLRI
                     entry. Set it to match what the session negotiated.";
                ze:help "Whether NLRI includes ADD-PATH path-id (RFC 7911)";
            }
        }
        output {
            leaf json {
                type string;
                description
                    "The text is one JSON document holding the attributes, the announced NLRI
                     and the withdrawn NLRI. It is the same shape a parsed update event carries.";
                ze:help "ze-bgp JSON with update attributes and NLRI";
            }
        }
    }

    // Runtime: Event emission (plugin-generated events).

    rpc emit-event {
        ze:method "ze-plugin-engine:emit-event";
        description "The engine routes the event to all plugins subscribed to the
matching namespace and event-type.";
        ze:help "Plugin emits a custom event to subscribers.";
        input {
            leaf namespace {
                type string;
                mandatory true;
                description
                    "The namespace MUST be one the event registry knows. An empty namespace, or
                     a namespace and type pair the registry does not hold, is refused.";
                ze:help "Event namespace (e.g., bgp, rib)";
            }
            leaf event-type {
                type string;
                mandatory true;
                description
                    "The type MUST be registered under the namespace. A subscriber that
                     subscribed to this type, or to *, receives the event.";
                ze:help "Event type (e.g., rpki, update)";
            }
            leaf direction {
                type string;
                default "received";
                description
                    "The engine matches the direction against each subscription's direction.
                     A subscription with no direction suffix matches both.";
                ze:help "Event direction (received, sent, both)";
            }
            leaf peer-address {
                type string;
                default "*";
                description
                    "With an address, the event is peer-scoped and goes through the same
                     delivery graph as the reactor's own events, so a peer's attach block
                     decides who receives it. With an empty value, every matching subscription
                     receives it.";
                ze:help "Peer address for event routing (* for all)";
            }
            leaf event {
                type string;
                mandatory true;
                description
                    "The text is delivered to each matching plugin as the event body. When the
                     type has a registered payload type and an engine subscriber, it is decoded
                     once for that subscriber.";
                ze:help "JSON-encoded event payload";
            }
        }
        output {
            leaf delivered {
                type uint32;
                description
                    "The count covers plugin processes alone. Engine-side subscribers run after
                     delivery and are not counted.";
                ze:help "Number of plugins that received the event";
            }
        }
    }

    // Error identities.

    identity registration-conflict {
        description "Family or command already claimed by another plugin";
    }

    identity stage-timeout {
        description "Barrier timeout exceeded during startup";
    }

    identity invalid-route {
        description "Route parsing failed";
    }
}
