module ze-log-cmd {
    namespace "urn:ze:log:cmd";
    prefix logcmd;
    import ze-extensions { prefix ze; }
    description "Log inspection and runtime level control. Owned by core/slogutil because these handlers read and configure the generic logging subsystem. See ai/rules/plugin-self-containment.md.";
    revision 2026-06-06 { description "Relocated from central cmd/log schema (plugin self-containment). Wire methods retain ze-bgp: prefix for compatibility."; }

    container show {
        config false;
        description "Read-only commands to inspect system, protocol, and network state";

        container log {
            config false;
            description "View log entries and current levels";

            container levels {
                config false;
                ze:command "ze-bgp:log-levels";
                description "Show what log level each subsystem is using.
Lists every registered logger with its current level. Use
'request log level' to change a level at runtime without restarting.";
            }

            container recent {
                config false;
                ze:command "ze-bgp:log-recent";
                description "Show recent log entries from the in-memory ring.
Filters (all optional): level <lvl>, component <name>, count <N>.
Newest entries first. Useful when you cannot access the log file
directly.";
                leaf level {
                    type enumeration {
                        enum disabled;
                        enum debug;
                        enum info;
                        enum warn;
                        enum err;
                    }
                    description "Filter by log level";
                }
                leaf component {
                    type string;
                    description "Filter by component name";
                }
                leaf count {
                    type uint32;
                    description "Maximum number of entries";
                }
            }
        }
    }

    container request {
        config false;
        description "Operational actions";

        container log {
            config false;
            description "Runtime log operations";

            container level {
                config false;
                ze:command "ze-bgp:log-set";
                description "Change a subsystem's log level without restarting.
Usage: request log level <logger> <level>. Takes effect immediately.
Set to debug when troubleshooting, then back to info when you are done.";
                leaf logger {
                    type string;
                    description "Logger/subsystem name";
                }
                leaf target {
                    type enumeration {
                        enum disabled;
                        enum debug;
                        enum info;
                        enum warn;
                        enum err;
                    }
                    description "Target log level";
                }
            }
        }
    }
}
