module ze-extensions {
    namespace "urn:ze:extensions";
    prefix ze;

    description "YANG extensions for ZeBGP config parsing syntax modes.
                 These extensions control how the config parser handles
                 nodes that need special syntax beyond standard YANG.";

    revision 2026-01-01 {
        description "Initial revision";
    }

    // Extension: syntax
    // Controls how the config parser handles this node.
    //
    // Values:
    //   flex           - accepts flag (;), value (word;), or block ({...})
    //   freeform       - accepts arbitrary words until ; or {}
    //   inline-list    - list with key + attributes on same line
    //   family-block   - special address family syntax (ipv4/unicast;)
    //   multi-leaf     - multiple space-separated values on one line
    //   bracket        - bracketed syntax [ a b c ] for leaf-list
    //   value-or-array - accepts either value; or [ a b c ];
    extension syntax {
        argument mode;
        description "Specifies the parsing syntax mode for this node.";
    }

    // Extension: key-type
    // For inline-list nodes, specifies the key type.
    //
    // Values: string, prefix, ip, uint32
    extension key-type {
        argument type;
        description "Specifies the key type for inline-list nodes.";
    }

    // Extension: route-attributes
    // Marker that this node accepts standard BGP route attributes.
    // Used on inline-list nodes for static/announce routes.
    extension route-attributes {
        description "Node accepts standard route attributes
                     (next-hop, origin, community, etc.)";
    }

    // Extension: allow-unknown-fields
    // Container accepts arbitrary key-value pairs beyond defined leaves.
    // Used for dynamic configuration like per-subsystem log levels.
    // Unknown fields are stored as key-value strings.
    extension allow-unknown-fields {
        description "Container accepts arbitrary unknown fields as strings.
                     Used for environment.log to allow subsystem paths
                     like 'bgp.routes debug;' for ze.log.bgp.routes=debug.";
    }

    // Extension: validate
    // References a registered Go function for runtime validation and completion.
    // Used only when YANG native constraints (enum, pattern, range) are insufficient —
    // primarily for runtime-determined valid sets (e.g., address families from plugins).
    // The argument is the validator function name registered via ValidatorRegistry.
    extension validate {
        argument name;
        description "References a custom validator function for runtime validation.
                     The function provides both Validate(path, value) and Complete()
                     for CLI tab-completion of valid values.";
    }
}
