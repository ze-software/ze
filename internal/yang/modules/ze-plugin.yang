module ze-plugin {
    namespace "urn:ze:plugin";
    prefix plug;

    import ze-extensions { prefix ze; }

    description "Plugin configuration for ZeBGP";

    revision 2026-01-01 {
        description "Initial revision";
    }

    container plugin {
        description "Plugin configuration";

        list external {
            key "name";
            description "External plugin process";

            leaf name {
                type string {
                    length "1..64";
                }
                description "Plugin name";
            }

            leaf run {
                ze:syntax "multi-leaf";
                type string;
                description "Command to execute plugin (with args)";
            }

            leaf encoder {
                type string;
                description "Event encoding format (json, text)";
            }

            leaf respawn {
                type boolean;
                description "Respawn on exit";
            }

            leaf timeout {
                type string;
                description "Startup timeout (e.g., 10s, 1m)";
            }
        }
    }
}
