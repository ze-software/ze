module ze-plugin-conf {
    namespace "urn:ze:plugin:conf";
    prefix plug;

    import ze-extensions { prefix ze; }
    import ze-hub-conf { prefix hub; }

    description "Plugin configuration for ZeBGP";

    revision 2026-01-01 {
        description "Initial revision";
    }

    container plugin {
        description "Plugin configuration";

        list external {
            key "name";
            description "External plugin process";

            leaf name {
                type string {
                    length "1..64";
                }
                description "Plugin name";
            }

            leaf run {
                type string;
                description "Command to execute plugin (with args)";
            }

            leaf encoder {
                type string;
                description "Event encoding format (json, text)";
            }

            leaf respawn {
                type boolean;
                description "Respawn on exit";
            }

            leaf timeout {
                type string;
                description "Startup timeout (e.g., 10s, 1m)";
            }
        }
    }

    // Plugin-owned environment settings — augment hub's environment container
    augment "/hub:environment" {
        container api {
            description "API settings";
            leaf ack { type boolean; }
            leaf chunk { type int32; }
            leaf encoder { type string; }
            leaf compact { type boolean; }
            leaf respawn { type boolean; }
            leaf terminate { type boolean; }
            leaf cli { type boolean; }
            leaf pipename { type string; }
            leaf socketname { type string; }
        }
    }
}
