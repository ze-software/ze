module ze-types {
    namespace "urn:ze:types";
    prefix zt;

    description "Common types for ZeBGP configuration";

    revision 2026-01-01 {
        description "Initial revision";
    }

    // Grouping for common route attributes used in announce/static/etc.
    grouping route-attributes {
        description "Common BGP route attributes";
        leaf next-hop { type string; ze:validate "nonzero-ipv4|literal-self"; description "Next hop address"; }
        leaf origin {
            type enumeration {
                enum igp { description "Interior Gateway Protocol"; }
                enum egp { description "Exterior Gateway Protocol"; }
                enum incomplete { description "Incomplete origin"; }
            }
            description "Origin attribute (RFC 4271 Section 4.3)";
        }
        leaf local-preference { type uint32; description "Local preference"; }
        leaf med { type uint32; description "Multi-Exit Discriminator"; }
        leaf-list community { type string; ze:validate "community-range"; description "BGP communities"; }
        leaf-list extended-community { type string; description "Extended communities"; }
        leaf-list large-community { type string; description "Large communities"; }
        leaf-list as-path { type string; description "AS path"; }
        leaf path-information { type string; description "Path information"; }
        leaf label { type string; description "MPLS label"; }
        leaf-list labels { type string; description "MPLS labels (RFC 8277)"; }
        leaf rd { type string; description "Route Distinguisher"; }
        leaf aggregator { type string; description "Aggregator attribute"; }
        container atomic-aggregate { presence "Atomic aggregate flag"; description "Atomic aggregate"; }
        leaf originator-id { type ipv4-address; description "Originator ID (RFC 4456)"; }
        leaf cluster-list { type string; description "Cluster list (RFC 4456)"; }
        leaf name { type string; description "Route name"; }
        leaf split { type string; description "Split horizon"; }
        leaf watchdog { type string; description "Watchdog name"; }
        container withdraw { presence "Withdraw flag"; description "Withdraw flag"; }
        leaf-list attribute { type string; description "Generic attributes"; }
        container bgp-prefix-sid { presence "BGP Prefix SID enabled"; description "BGP Prefix SID"; }
        container bgp-prefix-sid-srv6 { presence "SRv6 Prefix SID enabled"; description "SRv6 Prefix SID"; }
    }

    typedef ip-address {
        type union {
            type ipv4-address;
            type ipv6-address;
        }
        description "IPv4 or IPv6 address";
    }

    typedef ipv4-address {
        type string {
            pattern '(([0-9]|[1-9][0-9]|1[0-9][0-9]|2[0-4][0-9]|25[0-5])\.){3}'
                  + '([0-9]|[1-9][0-9]|1[0-9][0-9]|2[0-4][0-9]|25[0-5])';
        }
        description "IPv4 address in dotted-decimal format";
    }

    typedef ipv6-address {
        type string {
            pattern '([0-9a-fA-F]{0,4}:){2,7}[0-9a-fA-F]{0,4}'
                  + '|([0-9a-fA-F]{0,4}:){1,6}:[0-9a-fA-F]{0,4}'
                  + '|::([0-9a-fA-F]{0,4}:){0,5}[0-9a-fA-F]{0,4}';
        }
        description "IPv6 address";
    }

    typedef asn {
        type uint32 {
            range "1..4294967295";
        }
        description "Autonomous System Number (4-byte, RFC 6793)";
    }

    typedef asn2 {
        type uint16 {
            range "1..65535";
        }
        description "Autonomous System Number (2-byte legacy)";
    }

    typedef port {
        type uint16 {
            range "1..65535";
        }
        description "TCP/UDP port number";
    }

    typedef prefix-ipv4 {
        type string {
            pattern '(([0-9]|[1-9][0-9]|1[0-9][0-9]|2[0-4][0-9]|25[0-5])\.){3}'
                  + '([0-9]|[1-9][0-9]|1[0-9][0-9]|2[0-4][0-9]|25[0-5])'
                  + '/(([0-9])|([1-2][0-9])|(3[0-2]))';
        }
        description "IPv4 prefix in CIDR notation";
    }

    typedef prefix-ipv6 {
        type string {
            pattern '([0-9a-fA-F]{0,4}:){2,7}[0-9a-fA-F]{0,4}'
                  + '/([0-9]|[1-9][0-9]|1[0-1][0-9]|12[0-8])';
        }
        description "IPv6 prefix in CIDR notation";
    }

    typedef community {
        type string {
            pattern '[0-9]+:[0-9]+';
        }
        description "BGP standard community (AA:NN format)";
    }

    typedef large-community {
        type string {
            pattern '[0-9]+:[0-9]+:[0-9]+';
        }
        description "BGP large community (RFC 8092)";
    }

    typedef extended-community {
        type string {
            pattern '(target|origin):[0-9]+:[0-9]+';
        }
        description "BGP extended community (RFC 4360)";
    }

    typedef route-distinguisher {
        type string {
            pattern '([0-9]+:[0-9]+)|([0-9]+\.[0-9]+\.[0-9]+\.[0-9]+:[0-9]+)';
        }
        description "Route Distinguisher (Type 0 or Type 1)";
    }

    // IPC types

    typedef address-family {
        type string {
            pattern '[a-z0-9-]+/[a-z0-9-]+';
        }
        ze:validate "registered-address-family";
        description "AFI/SAFI string (e.g., ipv4/unicast, ipv6/unicast)";
    }

    typedef peer-selector {
        type string;
        description "Peer address, '*' for all, or comma-separated list";
    }

    typedef encoding-mode {
        type enumeration {
            enum text { description "Human-readable text encoding"; }
            enum hex { description "Hexadecimal encoding"; }
            enum b64 { description "Base64 encoding"; }
        }
        description "Encoding mode for route data";
    }

    typedef wire-format {
        type enumeration {
            enum hex { description "Hex bytes"; }
            enum base64 { description "Base64 bytes"; }
            enum parsed { description "Parsed JSON"; }
            enum full { description "Full detail JSON"; }
        }
        description "Wire format for message output";
    }

    typedef ack-mode {
        type enumeration {
            enum sync { description "Synchronous acknowledgment"; }
            enum async { description "Asynchronous acknowledgment"; }
        }
        description "Acknowledgment mode for commands";
    }

    // IPC groupings

    grouping peer-info {
        description "Peer information returned by peer-list and peer-show";
        leaf address { type ip-address; description "Peer IP address"; }
        leaf asn { type asn; description "Peer ASN"; }
        leaf local-as { type asn; description "Local ASN for this peer"; }
        leaf state { type string; description "FSM state (idle, connect, active, opensent, openconfirm, established)"; }
        leaf router-id { type ipv4-address; description "Peer router ID"; }
        leaf hold-time { type uint16; description "Negotiated hold time"; }
        leaf uptime { type uint32; description "Seconds since established"; }
    }

    grouping command-info {
        description "Command descriptor for introspection";
        leaf name { type string; description "Command name"; }
        leaf description { type string; description "Command help text"; }
        leaf args { type string; description "Argument specification"; }
        leaf source { type string; description "Source (builtin or plugin name)"; }
        leaf completable { type boolean; description "Supports tab completion"; }
    }

    grouping event-type-info {
        description "Event type descriptor for subscribe";
        leaf name { type string; description "Event type name"; }
        leaf description { type string; description "Event description"; }
    }

    grouping transaction-result {
        description "Result of a route transaction (commit-end)";
        leaf routes-announced { type uint32; description "Routes announced"; }
        leaf routes-withdrawn { type uint32; description "Routes withdrawn"; }
        leaf updates-sent { type uint32; description "UPDATE messages sent"; }
        leaf-list families { type address-family; description "Affected address families"; }
    }

    grouping cache-entry {
        description "Cached BGP message descriptor";
        leaf message-id { type uint64; description "Cache message ID"; }
        leaf peer { type ip-address; description "Source peer address"; }
        leaf age-ms { type uint32; description "Age in milliseconds"; }
        leaf size { type uint32; description "Message size in bytes"; }
    }

    typedef afi {
        type enumeration {
            enum ipv4 { value 1; description "IPv4 (AFI 1)"; }
            enum ipv6 { value 2; description "IPv6 (AFI 2)"; }
        }
        description "Address Family Identifier";
    }

    typedef safi {
        type enumeration {
            enum unicast { value 1; description "Unicast (SAFI 1)"; }
            enum multicast { value 2; description "Multicast (SAFI 2)"; }
            enum mpls { value 4; description "MPLS-labeled (SAFI 4)"; }
            enum mpls-vpn { value 128; description "MPLS VPN (SAFI 128)"; }
            enum flowspec { value 133; description "FlowSpec (SAFI 133)"; }
        }
        description "Subsequent Address Family Identifier";
    }
}
