module ze-cli-meta-cmd {
    namespace "urn:ze:cli:meta:cmd";
    prefix climeta;
    import ze-extensions { prefix ze; }
    description "Command discovery, help, and plugin session configuration. Bare verb-root anchor; all commands owned by component/command.";
    revision 2026-03-16 { description "Initial revision"; }
    revision 2026-06-06 { description "Relocated all meta commands to component/command (plugin self-containment). Bare anchor only."; }

    // NOTE: help, command discovery, event listing, and plugin session
    // configuration are owned by the command component.
    // See internal/component/command/schema/ze-command-meta-cmd.yang.
}
