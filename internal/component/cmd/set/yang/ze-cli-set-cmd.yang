module ze-cli-set-cmd {
    namespace "urn:ze:cli:set:cmd";
    prefix clisetcmd;
    import ze-extensions { prefix ze; }
    // This module is the bare verb-root anchor. component/host owns
    // set file-descriptors.
    description "Create or modify running configuration.";
    revision 2026-03-23 { description "Initial revision"; }
    // Peer config goes through the editor, and the parallel
    // runtime-then-persist path is dropped.
    revision 2026-06-03 { description "Removed set bgp peer with/save."; }
    // Plugin self-containment. This module keeps the bare anchor only.
    revision 2026-06-06 { description "Relocated set system file-descriptors to component/host."; }

    container set {
        config false;
        description "This keyword runs nothing on its own. It is the bare verb root, and each
owning module merges its own children onto it. 'set system file-descriptors' comes from
the host component.";
        ze:help "Modify running configuration parameters.";

        // NOTE: `set system file-descriptors` is owned by the host component.
        // See internal/component/host/schema/ze-host-set-cmd.yang.
    }
}
