module ze-cli-set-api {
  namespace "urn:ze:cli:set:api";
  prefix cli-set;

  description
    "Ze set verb RPCs -- create or modify configuration.";

  // 'set bgp peer with' and 'set bgp peer save' were removed on 2026-06-03,
  // which ze-cli-set-cmd.yang records in its revision of that date. The two
  // rpcs outlived the commands and published methods no handler answered. Peer
  // config goes through the editor, and the module now declares no rpc.
}
