module ze-cli-metrics-cmd {
    namespace "urn:ze:cli:metrics:cmd";
    prefix climetricscmd;
    import ze-extensions { prefix ze; }
    description "Prometheus metrics and attribute pool statistics";
    revision 2026-03-16 { description "Initial revision"; }

    container metrics {
        config false;
        description "Access Prometheus metrics and internal pool stats";

        container values {
            config false;
            ze:command "ze-bgp:metrics-values";
            description "Dump all metrics in Prometheus text format.
Outputs every registered metric with labels and values. Suitable
for feeding into Prometheus, Grafana, or curl-based monitoring.";
        }

        container list {
            config false;
            ze:command "ze-bgp:metrics-list";
            description "List all registered metric names (no values).
Useful for discovering what metrics exist before querying them.";
        }
    }
}
