module ze-metrics-cmd {
    namespace "urn:ze:metrics:cmd";
    prefix metricscmd;
    import ze-extensions { prefix ze; }
    description "BGP metrics command tree";
    revision 2026-03-16 { description "Initial revision"; }

    container metrics {
        config false;
        description "Metrics operations";

        container values {
            config false;
            ze:command "ze-bgp:metrics-values";
            description "Prometheus metrics (text format)";
        }

        container list {
            config false;
            ze:command "ze-bgp:metrics-list";
            description "List metric names";
        }
    }
}
