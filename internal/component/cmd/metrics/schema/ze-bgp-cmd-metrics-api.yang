module ze-bgp-cmd-metrics-api {
    namespace "urn:ze:bgp:cmd:metrics:api";
    prefix "bgp-metrics-api";

    organization "Ze Project";
    description "BGP metrics command RPCs.";
    revision 2026-03-10 {
        description "Initial revision.";
    }

    rpc metrics-show {
        description "Show Prometheus metrics in text format.";
    }

    rpc metrics-list {
        description "List metric names only.";
    }

    rpc pool-stats {
        description "Show per-attribute-pool occupancy and dedup rates.";
    }
}
