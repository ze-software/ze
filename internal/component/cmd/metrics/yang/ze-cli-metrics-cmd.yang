module ze-cli-metrics-cmd {
    namespace "urn:ze:cli:metrics:cmd";
    prefix climetricscmd;
    import ze-extensions { prefix ze; }
    description "Prometheus metrics and attribute pool statistics";
    revision 2026-03-16 { description "Initial revision"; }
    revision 2026-06-04 { description "Verb-first grammar: reads under show metrics."; }

    container show {
        config false;

        container metrics {
            config false;
            description "The metrics are the same series the Prometheus endpoint publishes, read here
                         without an HTTP client. The pool statistics are internal to Ze and are not
                         exported over that endpoint.";
            ze:help "Access Prometheus metrics and internal pool stats.";

            container values {
                config false;
                ze:command "ze-cmd:bgp-metrics-values";
                ze:rpc "ze-bgp-cmd-metrics-api:metrics-show";
                description "Outputs every registered metric with labels and values. Suitable
for feeding into Prometheus, Grafana, or curl-based monitoring.";
                ze:help "Dump all metrics in Prometheus text format.";
            }

            container list {
                config false;
                ze:command "ze-cmd:bgp-metrics-list";
                ze:rpc "ze-bgp-cmd-metrics-api:metrics-list";
                description "Useful for discovering what metrics exist before querying them.";
                ze:help "List all registered metric names (no values).";
            }
        }
    }
}
