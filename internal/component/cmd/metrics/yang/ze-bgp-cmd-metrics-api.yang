module ze-bgp-cmd-metrics-api {
    namespace "urn:ze:bgp:cmd:metrics:api";
    prefix "bgp-metrics-api";

    import ze-extensions { prefix ze; }

    organization "Ze Project";
    description "BGP metrics command RPCs.";
    revision 2026-03-10 {
        description "Initial revision.";
    }

    rpc metrics-show {
        description "The output is what the Prometheus HTTP handler writes for a GET on /metrics. It
carries every registered metric with its HELP and TYPE lines. When no Prometheus
registry is installed the RPC answers 'metrics not available'.";
        ze:help "Show Prometheus metrics in text format.";
    }

    rpc metrics-list {
        description "The names are sorted, and they carry no sample values beside them. Use
metrics-show for the values. When no Prometheus registry is installed the RPC
answers 'metrics not available'.";
        ze:help "List metric names only.";
    }
}
