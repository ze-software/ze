module ze-cli-log-cmd {
    namespace "urn:ze:cli:log:cmd";
    prefix clilogcmd;
    import ze-extensions { prefix ze; }
    description "View and control daemon logging. Bare verb-root anchor; all commands owned by core/slogutil.";
    revision 2026-03-16 { description "Initial revision"; }
    revision 2026-06-04 { description "Verb-first grammar: reads under show log, runtime mutation under request log level."; }
    revision 2026-06-06 { description "Relocated all log commands to core/slogutil (plugin self-containment). Bare anchor only."; }

    // NOTE: `show log levels`, `show log recent`, and `request log level`
    // are owned by core/slogutil.
    // See internal/core/slogutil/schema/ze-log-cmd.yang.
}
