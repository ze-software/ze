module ze-bgp-cmd-log-api {
    namespace "urn:ze:bgp:cmd:log:api";
    prefix "bgp-log-api";

    import ze-extensions { prefix ze; }

    organization "Ze Project";
    description "BGP log level command RPCs.";
    revision 2026-03-10 {
        description "Initial revision.";
    }

    rpc log-show {
        description "The answer is one level for each subsystem that registered a logger, and
the count beside it. A subsystem that has registered no logger is not listed.";
        ze:help "Show current log levels for all subsystems.";
    }

    rpc log-set {
        description "The subsystem name and the level are both required. The new level takes
effect at once and is not written to the configuration, so a restart returns the subsystem
to its configured level.";
        ze:help "Set log level for a subsystem at runtime.";
    }

    rpc log-recent {
        description "The buffer holds the entries in memory only, so it is empty after a
restart. The options are level, component and count, each one takes a value, and the count
must be a positive number.";
        ze:help "Show recent log entries from ring buffer with optional level/component/count filters.";
    }
}
