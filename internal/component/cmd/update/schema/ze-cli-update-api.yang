module ze-cli-update-api {
  namespace "urn:ze:cli:update:api";
  prefix cli-update;

  description
    "Ze update verb RPCs -- refresh stale data from external sources.";

  rpc bgp-peer-prefix { description "Update prefix maximums from PeeringDB for matched peer(s)"; }
  rpc system-firmware-check { description "Trigger immediate firmware version check"; }
  rpc system-firmware-download { description "Download firmware update now"; }
  rpc system-firmware-apply { description "Full firmware update cycle: download+verify+stage+restart"; }
  rpc system-firmware-restart { description "Restart into staged firmware version"; }
  rpc system-firmware-rollback { description "Restore previous firmware version and restart"; }
}
