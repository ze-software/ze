module ze-cli-update-cmd {
    namespace "urn:ze:cli:update:cmd";
    prefix cliupdatecmd;
    import ze-extensions { prefix ze; }
    description "Refresh data from external sources and manage firmware updates. Bare verb-root anchor; firmware commands owned by component/update.";
    revision 2026-03-23 { description "Initial revision"; }
    revision 2026-06-03 { description "Removed update bgp peer prefix (PeeringDB lookup stays in resolve; applying limits goes through the editor)."; }
    revision 2026-06-06 { description "Relocated firmware commands to component/update (plugin self-containment). Bare anchor only."; }

    container update {
        config false;
        description "Pull fresh data from external sources or manage firmware";

        // NOTE: `update system firmware *` commands are owned by the update component.
        // See internal/component/update/schema/ze-update-firmware-cmd.yang.
    }
}
