module ze-cli-commit-cmd {
    namespace "urn:ze:cli:commit:cmd";
    prefix clicommitcmd;
    import ze-extensions { prefix ze; }
    description "BGP commit command tree";
    revision 2026-03-16 { description "Initial revision"; }

    container commit {
        config false;
        ze:command "ze-bgp:commit";
        description "Named commit operations. Grammar: commit <action> <name> [args].
                     Actions: list, start, end, eor, rollback, show, withdraw.";
    }
}
