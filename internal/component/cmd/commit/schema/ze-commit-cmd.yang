module ze-commit-cmd {
    namespace "urn:ze:commit:cmd";
    prefix commitcmd;
    import ze-extensions { prefix ze; }
    description "BGP commit command tree";
    revision 2026-03-16 { description "Initial revision"; }

    container commit {
        config false;
        ze:command "ze-bgp:commit";
        description "Named commit operations";
    }
}
