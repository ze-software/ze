module ze-cli-clear-api {
  namespace "urn:ze:cli:clear:api";
  prefix cli-clear;

  import ze-extensions { prefix ze; }

  // The state a clear RPC resets is a kernel counter, an ARP entry, or a BGP
  // session statistic. The clear verb differs from `del`: nothing is removed
  // from the running config, and only accumulated runtime state is zeroed.
  description
    "Ze clear verb RPCs: reset per-object operational state without changing
     configuration.";

  rpc interface-counters {
    description "clear interface counters all clears every interface, and clear
interface name <name> counters clears one. The bare clear interface counters is
refused, because it names no target and Ze never clears everything unless all is
typed. Ze first
asks the backend to zero the kernel counters. When the backend answers that
the counters cannot be reset, Ze records the current values as a baseline and
subtracts it from later reads. That baseline is held in memory, so a restart
of Ze brings the raw kernel counts back.";
    ze:help "Reset RX/TX counters on one or all interfaces.";
  }
  rpc dns-cache {
    description "clear dns cache all empties every cached record and resets all
four counters (hits, misses, evictions and expired). It takes no argument. The
bare clear dns cache is refused, because it names no target. Two sibling
commands act more narrowly. 'clear dns cache stats' zeroes the counters and keeps the records,
and 'clear dns cache record <name>' deletes one name.";
    ze:help "Flush DNS cache entries or reset cache counters.";
  }
}
