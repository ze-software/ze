module ze-cli-subscribe-cmd {
    namespace "urn:ze:cli:subscribe:cmd";
    prefix clisubcmd;
    import ze-extensions { prefix ze; }
    description "Subscribe to and unsubscribe from daemon events";
    revision 2026-03-16 { description "Initial revision"; }

    container request {
        config false;

        container subscribe {
            config false;
            ze:command "ze-bgp:subscribe";
            ze:task-support required;
            description "Start receiving events of one or more types.
Events are delivered asynchronously to your plugin session until
you unsubscribe. Use 'event list' to see available event types.";
        }

        container unsubscribe {
            config false;
            ze:command "ze-bgp:unsubscribe";
            description "Stop receiving events you previously subscribed to.
Removes the subscription for the specified event type from your
current plugin session.";
        }
    }
}
