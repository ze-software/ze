module ze-cli-subscribe-cmd {
    namespace "urn:ze:cli:subscribe:cmd";
    prefix clisubcmd;
    import ze-extensions { prefix ze; }
    description "Subscribe to and unsubscribe from daemon events";
    revision 2026-03-16 { description "Initial revision"; }

    container request {
        config false;

        container subscribe {
            config false;
            ze:command "ze-cmd:bgp-subscribe";
            ze:rpc "ze-bgp-api:subscribe";
            ze:task-support required;
            description "Events are delivered asynchronously to your plugin session until
you unsubscribe. Use 'show event list' to see available event types.";
            ze:help "Start receiving events of one or more types.";
        }

        container unsubscribe {
            config false;
            ze:command "ze-cmd:bgp-unsubscribe";
            ze:rpc "ze-bgp-api:unsubscribe";
            description "Removes the subscription for the specified event type from your
current plugin session.";
            ze:help "Stop receiving events you previously subscribed to.";
        }
    }
}
