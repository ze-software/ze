module ze-bgp-cmd-subscribe-api {
    namespace "urn:ze:bgp:cmd:subscribe:api";
    prefix "bgp-sub-api";

    import ze-extensions { prefix ze; }

    organization "Ze Project";
    description "BGP event subscription RPCs.";
    revision 2026-03-08 {
        description "Initial revision.";
    }

    rpc subscribe {
        description "Ze marks the subscription as a runtime override. The daemon
then delivers the events whether or not the config grants that type. The next
config apply discards the override, so the config document stays the durable
record of what the daemon feeds.";
        ze:help "Subscribe to events matching filter criteria.";
    }
    rpc unsubscribe {
        description "Ze drops the first subscription that matches, whether a
runtime subscribe command added it or the config granted it. The answer
carries a removed field, and that field is false when nothing matched.";
        ze:help "Unsubscribe from event subscriptions.";
    }
}
