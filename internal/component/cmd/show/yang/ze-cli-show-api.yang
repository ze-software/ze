module ze-cli-show-api {
  namespace "urn:ze:cli:show:api";
  prefix cli-show;

  import ze-extensions { prefix ze; }

  description
    "Ze show verb RPCs -- read-only introspection commands.";

  // l2tp-health and bgp-health were declared here, in an always-linked
  // module, while only the gated L2TP and BGP components answer them.
  revision 2026-10-21 {
    description "Move l2tp-health to ze-l2tp-api and bgp-health to ze-bgp-api, their owners.";
  }

  rpc bgp-warnings {
    description "Two codes reach this answer. Ze raises prefix-stale where a peer's
prefix data is old, and prefix-threshold where a family's prefix count passes
the warning limit. Both live on the report bus under the bgp source, and 'show
warnings' reads that same bus for every subsystem.";
    ze:help "Show active prefix warnings (stale data, threshold exceeded).";
  }
  rpc traffic {
    description "Give an interface name to read the qdisc type, the class count and
the default class of that one interface. With no name, Ze reads every
interface. A platform with no traffic control backend fails with 'traffic
control not available on this platform'.";
    ze:help "Show traffic control state per interface.";
  }
  rpc event-recent {
    description "Each row carries the timestamp, the namespace and the event type,
and it does not carry the payload. 'namespace <name>' reads one namespace and
'count <N>' caps the rows. The ring holds a bounded history, so an event that
aged out is gone.";
    ze:help "Show recent events from global event ring.";
  }
  rpc event-namespaces {
    description "Each row carries a namespace and the number of events the ring
holds for it. The rows are sorted by namespace name. A namespace with no event
in the ring does not appear.";
    ze:help "Show registered event namespaces with counts.";
  }
  rpc event-delivery {
    description "Ze reads the index delivery reads, and not the config document, so
the answer is what the daemon acts on. A granted token the event registry does
not know appears under unresolved, which is the one way an edge goes missing.";
    ze:help "Show which peers feed which attached processes.";
  }
  rpc metrics-query {
    description "Ze renders the Prometheus registry and then filters its text
lines. Each label filter is written 'label <key> <value>', filters repeat, and
Ze ANDs them. A key named twice states two conditions and matches nothing,
which is deliberate.";
    ze:help "Query Prometheus metrics by name and label filter.";
  }
  rpc ping {
    description "The count is 5 without a value and its range is 1 to 100. The
timeout is 5 seconds without a value and its range is 1s to 30s. The payload
size range is 1 to 65507 bytes, and the engine picks the size where none is
given.";
    ze:help "ICMP ping from the router to a destination IP.";
  }
  rpc route-lookup {
    description "Ze asks the kernel FIB through the netlink backend, so the answer
is the route the kernel picks and not the BGP RIB entry. Give one IP address.
An address it cannot parse fails with 'invalid destination'.";
    ze:help "Longest-prefix-match route lookup for a destination IP.";
  }
  rpc capture {
    description "Without a protocol word, Ze answers for both l2tp and bgp. 'peer
<address>' and 'count <N>' narrow the answer, and 'tunnel-id <id>' narrows the
l2tp half. The l2tp half needs the ze_l2tp build tag and is absent from a
build without it.";
    ze:help "Show captured control messages.";
  }
  rpc health {
    description "The answer carries an overall status, one row per component and a
checked-at time. A component row carries a reason only where the component
reported one.";
    ze:help "Show aggregated component health status.";
  }
}
