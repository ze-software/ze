module ze-cli-show-cmd {
    namespace "urn:ze:cli:show:cmd";
    prefix clishowcmd;
    import ze-extensions { prefix ze; }
    description "Show command tree for read-only inspection of system and protocol state";
    // The packed label=value form put a keyword from an open set inside a value
    // token.
    revision 2026-08-29 { description "show metrics name takes its label filters as two tokens: label <key> <value>, repeatable."; }
    // The description spelled the name in prose and the model stated nothing.
    revision 2026-08-29 { description "Declare the metric name show metrics name reads."; }
    revision 2026-03-26 { description "Initial revision"; }
    // show dns lookup/cache went to resolve, and show bgp-health to the bgp peer
    // command owner, for plugin self-containment.
    revision 2026-06-03 { description "Relocated show dns lookup/cache and show bgp-health out of this central schema."; }
    // host, ntp, conntrack, update, kernel-log, capture, tcp-check, doctor,
    // crashes, config, data, env, schema, yang, policy-chain and policy-test, for
    // plugin self-containment.
    revision 2026-06-06 { description "Relocated 16 commands to their owning components and plugins."; }

    container show {
        config false;
        description "Nothing under show changes state, so every one of them is safe against a router
                     carrying traffic. The verbs that do change something are clear, request, set,
                     delete, create and update.";
        ze:help "Read-only commands to inspect system, protocol, and network state.";

        container version {
            config false;
            ze:command "ze-cmd:show-version";
            description "You can verify which release is deployed on this box.";
            ze:help "Show the running Ze version and build date.";
        }

        container uptime {
            config false;
            ze:command "ze-cmd:show-uptime";
            description "Returns the start time and elapsed uptime. Handy after a maintenance
window to confirm the process restarted.";
            ze:help "Show how long the daemon has been running.";
        }

        container reload-status {
            config false;
            ze:command "ze-cmd:show-reload-status";
            description "Returns a generation counter, the outcome of the most recent reload
(applied or failed), and when it finished. The counter advances on every
processed reload, including one that rejected or changed nothing, so you
can confirm a SIGHUP was acted on even when it deliberately left the
running config alone.";
            ze:help "Show how many config reloads the daemon has processed.";
        }

        container runtime {
            config false;
            description "This reports the process rather than the protocol: goroutines, heap and garbage
                         collection. It is for diagnosing the daemon itself, and it says nothing about a
                         peer or a route.";
            ze:help "Go runtime internals of the daemon process.";

            container memory {
                config false;
                ze:command "ze-cmd:show-system-memory";
                description "Returns allocated bytes, heap in-use, total allocations, GC cycles, and
last GC pause duration. Compare over time to spot leaks. For the OS-level
process memory (RSS/VSZ) use 'show system memory'.";
                ze:help "Show the Go runtime allocator memory stats.";
            }
        }

        container system {
            config false;
            description "This reports the daemon and the host it runs on, not the protocols it speaks. A
                         peer, a route or an interface is under its own noun.";
            ze:help "Daemon process and runtime diagnostics.";

            container memory {
                config false;
                ze:command "ze-cmd:show-system-memory-map";
                description "Returns VmRSS, VmSize, VmSwap, and thread count from /proc/self/status
(Linux only). This is what the operating system reports the process is
using. For the Go runtime allocator view (heap, GC), use
'show runtime memory'.";
                ze:help "Show how much memory the daemon is using, from the OS's view.";
            }

            container cpu {
                config false;
                ze:command "ze-cmd:show-system-cpu";
                description "Returns goroutine count, logical CPU count, and GOMAXPROCS setting.
Useful when the box feels sluggish and you want to see if Ze is
hogging threads.";
                ze:help "Show CPU utilization context for the daemon.";
            }

            container date {
                config false;
                ze:command "ze-cmd:show-system-date";
                description "Useful for correlating log timestamps when the box is in a
different timezone than you are.";
                ze:help "Show the daemon's current wall-clock time and timezone.";
            }

            container platform {
                config false;
                ze:command "ze-cmd:show-system-platform";
                description "Reports whether this is gokrazy, systemd, container, plain-linux, or
darwin, along with platform-specific capabilities.";
                ze:help "Show what kind of platform the daemon is running on.";
            }

            container subsystem {
                config false;
                description "A subsystem is a registered component of the daemon. What is listed
                             depends on the build and on the plugins that loaded. It does not
                             depend on the configuration alone.";
                ze:help "Subsystem lifecycle and state.";

                container list {
                    config false;
                    ze:command "ze-cmd:show-system-subsystem-list";
                    description "Shows you which components (bgp, dns, web, l2tp, etc.) are active,
stopped, or failed.";
                    ze:help "List every registered subsystem and whether it is running.";
                }
            }

            // NOTE: `show system ntp` is owned by the NTP plugin.
            // See internal/plugins/ntp/yang/ze-ntp-cmd.yang.

            // NOTE: `show system conntrack` is owned by the firewall component.
            // See internal/component/firewall/schema/ze-firewall-cmd.yang.

            // NOTE: `show system update` is owned by the update-cmd plugin.
            // See internal/plugins/update-cmd/yang/ze-update-show-cmd.yang.

            container sockets {
                config false;
                ze:command "ze-cmd:show-system-sockets";
                description "Every filter is optional and they combine. States use
kernel names (ESTABLISHED, LISTEN, TIME_WAIT).
Linux only. Good for confirming listeners or spotting stuck connections.";
                ze:help "Show open TCP and UDP sockets on this box.";
                leaf protocol {
                    type enumeration {
                        enum tcp { ze:help "List only TCP sockets, IPv4 and IPv6."; }
                        enum udp { ze:help "List only UDP sockets, IPv4 and IPv6."; }
                    }
                    description "The word is optional. Absent, the list carries both protocols. Ze reads
/proc/net/tcp and /proc/net/tcp6 for tcp, and the udp pair for udp.";
                    ze:help "Filter by protocol.";
                }
                leaf state {
                    type string;
                    description "The value is a kernel state name such as established, listen or time_wait,
in any letter case. Only sockets in that state are listed. A UDP socket has no state
to match.";
                    ze:help "Filter by socket state.";
                }
                leaf port {
                    type uint32;
                    description "The value is a port number from 1 to 65535. A socket is listed when its
local port or its remote port equals it. A value outside that range is ignored and the
list is not filtered.";
                    ze:help "Filter by port number.";
                }
            }

            // NOTE: `show system kernel-log` is owned by the host-cmd plugin.
            // See internal/plugins/host-cmd/yang/ze-host-cmd.yang.

            container goroutines {
                config false;
                ze:command "ze-cmd:show-system-goroutines";
                description "Modes: summary (groups by state), blocked (only lock/channel waiters),
full (all stacks). Default: summary. Share the output with support
when the daemon stops responding.";
                ze:help "Dump goroutine stacks for debugging hangs or deadlocks.";
                leaf mode {
                    type enumeration {
                        enum summary { ze:help "Report the goroutine total and a count for each state."; }
                        enum blocked { ze:help "List the goroutines waiting on a channel, a lock or I/O."; }
                        enum full { ze:help "Dump every goroutine stack as the Go runtime prints it."; }
                    }
                    description "The word is optional and the default is summary. The blocked list carries
each waiting goroutine with its id, its state and its stack, after the same totals. A
full dump is one text block of up to 16 MB, so keep it for a hang.";
                    ze:help "Display mode.";
                }
            }

            container file-descriptors {
                config false;
                ze:command "ze-cmd:show-system-file-descriptors";
                description "Summary mode: totals by type (socket, pipe, file). Detail mode: every
fd with its path and type. Linux only (reads /proc/self/fd). Check
this when you suspect fd exhaustion.";
                ze:help "Show how many file descriptors the daemon has open.";
                leaf mode {
                    type enumeration {
                        enum summary { ze:help "Report the total, a count per type, and the soft and hard limits."; }
                        enum detail { ze:help "Add one row per descriptor with its number, target and type."; }
                    }
                    description "The word is optional and the default is summary. Detail keeps the totals
and appends the descriptor rows, so the output grows with the number of open files.";
                    ze:help "Display mode.";
                }
            }

            container profile {
                config false;
                ze:command "ze-cmd:show-system-profile";
                description "Types: cpu (requires duration, e.g. 30s), heap, goroutine, allocs
(instant snapshots). Output is pprof format you can open with
'go tool pprof'. Send the file to support for deep analysis.";
                ze:help "Capture a runtime profile for performance analysis.";
                leaf type {
                    type enumeration {
                        enum cpu { ze:help "Sample the CPU for the duration, then return the profile."; }
                        enum heap { ze:help "Snapshot the live heap objects at the last garbage collection."; }
                        enum goroutine { ze:help "Snapshot the stack of every goroutine now."; }
                        enum allocs { ze:help "Sample the allocations made since the daemon started."; }
                    }
                    description "The word is optional and the default is heap. Only cpu runs for a time
and reads duration. The three others return at once. The response carries the pprof
bytes as base64 in data, with format pprof-base64.";
                    ze:help "Profile type.";
                }
                leaf duration {
                    type string {
                        pattern '\d+[smh]?';
                    }
                    description "The value is a Go duration with a unit, from 1s to 60s, and the default
is 10s. Only a cpu profile reads it. A second cpu profile is refused while one runs.";
                    ze:help "Profile duration.";
                }
            }

        }

        // NOTE: `show host` subtree is owned by the host-cmd plugin.
        // See internal/plugins/host-cmd/yang/ze-host-cmd.yang.

        // NOTE: the `show gnmi` command is owned by the gNMI component
        // so that removing gNMI removes it (no dangling command node).
        // `show gnmi` lives in internal/component/gnmi/schema/ze-gnmi-cmd.yang
        // next to its handler. The central show schema declares no
        // `container gnmi`. See ai/rules/plugin-self-containment.md.

        container warnings {
            config false;
            ze:command "ze-cmd:show-warnings";
            ze:rpc "ze-cli-show-api:bgp-warnings";
            description "Displays any conditions that need your attention (degraded peers,
resource limits approaching, etc.). Use 'source <name>' to filter
to a single subsystem.";
            ze:help "Show active warnings across all subsystems.";
        }

        // NOTE: the `show aaa` subtree is owned by the AAA component
        // so that removing AAA removes it (no dangling command node).
        // `show aaa accounting` lives in
        // internal/component/aaa/schema/ze-aaa-cmd.yang next to its
        // handler. The central show schema declares no `container aaa`.
        // See ai/rules/plugin-self-containment.md.

        container audit {
            config false;
            ze:command "ze-cmd:show-audit";
            description "Returns audit log entries with timestamps, actors, and actions.
Filters (all optional, combinable): action <type>, actor <name>,
surface <name> (cli, web, api), since/until <RFC3339>, count <N>.
Actions include config-commit, login, peer-teardown, and more.";
            ze:help "Show who did what and when on this box.";
            leaf action {
                type string;
                description "The value is an action name as the action column reports it, such as
config-commit or login, compared as text. Absent, entries of every action are shown.";
                ze:help "Filter by action type";
            }
            leaf actor {
                type string;
                description "The value is the name of the user or process that acted, compared as text
with the actor column. Absent, entries of every actor are shown.";
                ze:help "Filter by actor name";
            }
            leaf surface {
                type string;
                description "The value is the surface the action came through: cli, web or api,
compared as text. Absent, entries of every surface are shown.";
                ze:help "Filter by surface name";
            }
            leaf since {
                type string;
                description "The value is an RFC 3339 timestamp such as 2026-09-15T08:00:00Z, and any other
form is refused. Entries recorded before it are left out.";
                ze:help "Start time (RFC3339)";
            }
            leaf until {
                type string;
                description "The value is an RFC 3339 timestamp such as 2026-09-15T18:00:00Z, and any other
form is refused. Entries recorded after it are left out.";
                ze:help "End time (RFC3339)";
            }
            leaf count {
                type uint32;
                description "The value is a whole number of 1 or more. The query stops after that many
matching entries, oldest first. Absent, every matching entry is shown.";
                ze:help "Maximum number of entries";
            }
        }

        container errors {
            config false;
            ze:command "ze-cmd:show-errors";
            description "This is the first place to look when something goes wrong. Filter
with source <name> to narrow to one subsystem, count <N> to limit
output.";
            ze:help "Show recent errors across all subsystems, newest first.";
        }

        // NOTE: `show tcp-check` is owned by the diag plugin.
        // See internal/plugins/diag/yang/ze-diag-cmd.yang.

        container health {
            config false;
            ze:command "ze-cmd:show-health";
            ze:rpc "ze-cli-show-api:health";
            description "Returns per-component health (bgp, fib, iface, plugins, l2tp, etc.)
plus an overall status. Each component reports healthy, degraded, or
unhealthy with a reason. Start here when troubleshooting.
This runs a probe NOW and reports what the daemon is doing at this
moment. 'show plugin list' answers the other question, by replaying the setup
outcome each plugin recorded once, before main(), when it set itself up.";
            ze:help "Show the health of every component and the overall status of this box.";
        }

        // NOTE: `show doctor` is owned by the doctor plugin.
        // See internal/component/doctor/schema/ze-doctor-cmd.yang.

        container metrics {
            config false;
            ze:help "Access Prometheus metrics and internal pool stats.";

            container name {
                config false;
                ze:command "ze-cmd:show-metrics-query";
                ze:rpc "ze-cli-show-api:metrics-query";
                description "Returns matching time series from the internal registry. Multiple label
filters are ANDed. More targeted than the full metrics dump.";
                ze:help "Show one Prometheus metric by name.";
                leaf name {
                    type string { length "1..128"; }
                    mandatory true;
                    description "The value is the whole metric name, such as ze_bgp_connect_retry_counter,
compared as text with the start of each sample line. A name that matches no sample answers
an empty list.";
                    ze:help "Prometheus metric name";
                }

                container label {
                    config false;
                    ze:modifier "repeat";
                    description "Every filter given must match.";
                    ze:help "A label and the value it must hold for a series to be reported.";
                    leaf key {
                        type string { length "1..128"; }
                        mandatory true;
                        description "The value is a label name as the sample line carries it, such as peer.
A key named twice states two conditions, and a series MUST meet both.";
                        ze:help "Prometheus label name";
                    }
                    leaf value {
                        type string { length "1..256"; }
                        mandatory true;
                        description "The value is compared as text with the quoted label value on the sample
line, so it MUST be spelled the way the exporter wrote it.";
                        ze:help "The value the label must hold";
                    }
                }
            }
        }

        // NOTE: `show capture` subtree is owned by the diag plugin.
        // See internal/plugins/diag/yang/ze-diag-cmd.yang.

        container event {
            config false;
            description "The history is what the daemon kept in memory, so it starts at the last restart
                         and it is bounded. A namespace listed here is one some component registered, not
                         one an operator declared.";
            ze:help "Internal event history and namespace discovery.";

            container recent {
                config false;
                ze:command "ze-cmd:show-event-recent";
                ze:rpc "ze-cli-show-api:event-recent";
                description "Each event includes timestamp, namespace, and type. Filter with
namespace <name> to focus on one area, count <N> to limit output.
Useful for reconstructing what happened before an incident.";
                ze:help "Show recent events, newest first.";
            }

            container namespaces {
                config false;
                ze:command "ze-cmd:show-event-namespaces";
                ze:rpc "ze-cli-show-api:event-namespaces";
                description "Tells you which subsystems are generating events and how active
they are.";
                ze:help "List all event namespaces and how many events each has logged.";
            }

            container delivery {
                config false;
                ze:command "ze-cmd:show-event-delivery";
                ze:rpc "ze-cli-show-api:event-delivery";
                description "One block per peer, one row per `attach process` block on it: the
event types that process is fed, and the message types it may send
toward that peer. A token the event registry does not know is listed
as unresolved and carries no edge. Answer to 'why does my program
see nothing from this peer'.";
                ze:help "Show which peers feed which attached processes.";
            }
        }

        // NOTE: the entire `show bgp ...` subtree is owned by the BGP command
        // packages so that removing the BGP surface removes it (no dangling
        // command node). `show bgp peer ...` and `show bgp rib ...` live in
        // internal/component/bgp/plugins/cmd/{peer,rib}/schema; the offline
        // `show bgp decode` / `show bgp encode` diagnostics live in
        // cmd/ze/bgp/schema next to their handlers. The central show schema
        // declares no `container bgp`. See ai/rules/plugin-self-containment.md.

        // NOTE: `show env` subtree is owned by the env plugin.
        // See internal/plugins/env/yang/ze-env-cmd.yang.

        // NOTE: `show schema` subtree is owned by the config-schema plugin.
        // See internal/plugins/config-schema/yang/ze-schema-cli-cmd.yang.

        // NOTE: `show yang` subtree is owned by the config-yang plugin.
        // See internal/plugins/config-yang/yang/ze-yang-cli-cmd.yang.

        // NOTE: `show data` subtree is owned by the config-storage plugin.
        // See internal/plugins/config-storage/yang/ze-storage-cli-cmd.yang.

        // NOTE: `show config` subtree is owned by the config-cli plugin.
        // See internal/plugins/config-cli/yang/ze-config-cli-cmd.yang.

        container policy {
            config false;
            // No text on this container. ze-policy-cmd owns show policy and
            // states both halves, and a second module that restates one half
            // is what mergeHelpText reports as a mismatch.

            container list {
                config false;
                ze:command "ze-cmd:show-policy-list";
                description "Shows each filter type and its implementing plugin. Check here
when building a new policy chain to see what filters you can use.";
                ze:help "List all available filter types and named instances.";
            }

            // NOTE: `show policy chain` and `show policy test` are owned
            // by the BGP plugin.
            // See internal/component/bgp/plugins/cmd/policy/schema/ze-policy-cmd.yang.
        }

        // NOTE: `show crashes` is owned by the crashes plugin.
        // See internal/plugins/crashes/yang/ze-crashes-cmd.yang.

        // NOTE: the `show mpls ...` subtree is owned by the MPLS component
        // so that removing MPLS removes it (no dangling command node).
        // `show mpls forwarding` lives in
        // internal/component/mpls/schema/ze-mpls-cmd.yang next to its
        // handler. See ai/rules/plugin-self-containment.md.

        // NOTE: the `show storage ...` subtree is owned by the storage
        // component so that removing storage removes it (no dangling
        // command node). `show storage smart` lives in
        // internal/component/storage/schema/ze-storage-cmd.yang next to
        // its handler. The central show schema declares no `container
        // storage`. See ai/rules/plugin-self-containment.md.

    }
}
