module ze-config-archive-cmd {
    namespace "urn:ze:config:archive:cmd";
    prefix cfgarchivecmd;
    import ze-extensions { prefix ze; }
    description "Config archive command tree";
    revision 2026-05-17 { description "Initial revision"; }

    container config {
        config false;
        description "Configuration operations";

        container archive {
            config false;
            ze:command "ze-config-archive:trigger";
            description "Trigger a named config archive";
        }
    }
}
