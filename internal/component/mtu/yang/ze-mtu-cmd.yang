module ze-mtu-cmd {
    namespace "urn:ze:mtu:cmd";
    prefix mtucmd;
    import ze-types { prefix zt; }
    import ze-extensions { prefix ze; }
    // The dedicated mtu module owns the whole path-MTU diagnostic surface, so
    // dropping the plugin removes the command. Its subtree container-merges
    // onto the show verb root. See ai/rules/plugins.md.
    description "The path MTU diagnostic command tree: show mtu and show mtu host.";
    revision 2026-09-16 { description "Declare show mtu, its host address and its exhaustive and detail words."; }

    container show {
        config false;
        ze:help "Read-only commands to inspect system, protocol, and network state.";

        container mtu {
            config false;
            ze:command "ze-mtu:show-mtu";
            description "Measures the path MTU to every configured IPsec peer and to the reference
address, derives the ESP ceiling of each tunnel from its negotiated transform,
and reports whether each tunnel interface is oversized, tight, under-utilized
or correct, with the configuration commands that fix it. The run changes
nothing on the router. With host <address>, one address is measured instead
of the peers.";
            ze:help "Measure the path MTU and size the IPsec tunnels from it.";
            leaf host {
                type zt:ip-address;
                description "The value follows the host keyword and is one IPv4 or IPv6 address. Ze
measures the path MTU to that address alone and skips the peers and the
reference address. A name is refused: the run sends probes to the address as
typed.";
                ze:help "Measure one address instead of the IPsec peers.";
            }
            leaf search {
                type enumeration {
                    enum exhaustive { ze:help "Probe every size on the wire; discard the cached path MTU and the router's reported value."; }
                }
                description "The bare word exhaustive makes the run slower and its figure comes from
probing every size on the wire: the path MTU the kernel remembered and the
value a router reported are both discarded, so a stale or poisoned cache value
cannot reach the answer.";
                ze:help "exhaustive: a slower run that probes every size and discards the cached and reported path MTU.";
            }
            leaf view {
                type enumeration {
                    enum detail { ze:help "Report every probe size tried and every reply received, per target."; }
                }
                description "The bare word detail adds, per target, the size of every probe sent and
the answer each one received, so an operator can follow how the value was
found.";
                ze:help "detail: report every probe sent and every reply received.";
            }
        }
    }
}
