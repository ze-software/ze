module ze-lg-conf {
    namespace "urn:ze:lg:conf";
    prefix lg;

    import ze-types { prefix zt; }
    import ze-extensions { prefix ze; }

    description "Looking glass configuration for Ze";

    revision 2026-01-01 {
        description "Initial revision";
    }

    container environment {
        description "The looking-glass container under it carries every looking glass
                     setting: the enable switch, the listen endpoints, the TLS switch and
                     the bearer token.";
        ze:help "Environment settings for the looking glass.";

        container looking-glass {
            description "The container holds the enable switch, the listen endpoints, the
                         TLS switch and the bearer token.";
            ze:help "Looking glass HTTP server settings.";

            leaf enabled {
                type boolean;
                default false;
                description "The looking glass does not start while this leaf is false,
                             and false is the default.";
                ze:help "Enable the looking glass.";
            }

            list server {
                key "name";
                ze:listener;
                description "Each entry names one listen endpoint. The default endpoint
                             is 0.0.0.0 on port 8443.";
                ze:help "Looking glass listen endpoints.";

                leaf name {
                    type string;
                    description "The name is the list key, so each server entry carries a
                                 different one.";
                    ze:help "Server instance name.";
                }

                uses zt:listener {
                    refine ip {
                        default "0.0.0.0";
                    }
                    refine port {
                        default 8443;
                    }
                }
            }

            leaf tls {
                type boolean;
                default true;
                description "Self-signed TLS certificates persist in the configuration store. The default
                             true holds because the looking glass binds 0.0.0.0 and
                             publishes route data. Set it to false to serve plaintext,
                             for example when a proxy in front of Ze serves TLS.";
                ze:help "Enable TLS. Override with the ze.looking-glass.tls variable.";

            }

            leaf certificate {
                ze:reference "pki-certificate";
                type string {
                    length "1..255";
                    pattern '[A-Za-z0-9._-]+';
                }
                description
                    "The listener sends the leaf certificate and every
                     intermediate certificate the store entry holds, so a client
                     can build the full chain.
                     When this leaf is not set, ze generates a self-signed
                     certificate and serves that.
                     If the store holds no entry with that name, or the entry
                     holds no private key, ze exits with an error and rejects a
                     reload. ze never falls back to a self-signed certificate
                     for a configured name.
                     A named certificate comes from the pki container.
                     Environment variable: ze.looking-glass.certificate.";
                ze:help
                    "PKI store certificate served on the looking-glass listener (ze.looking-glass.certificate).";
            }

            leaf token {
                type string;
                ze:sensitive;
                description "Ze compares the token in constant time, with sha256 and
                             subtle.ConstantTimeCompare. An empty token leaves the
                             looking glass open, and that is the default: a looking
                             glass is a public read-only surface.";

                ze:help "Bearer token checked on every /api/ and /lg/ route (ze.looking-glass.token).";

            }
        }
    }
}
