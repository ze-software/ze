module ze-firewall-cmd {
    namespace "urn:ze:firewall:cmd";
    prefix firewallcmd;
    import ze-extensions { prefix ze; }
    description "Firewall show commands: ruleset inspection and address/port group listing.
         Relocated from the central show schema for plugin self-containment.";
    revision 2026-06-03 { description "Initial revision: relocated from ze-cli-show-cmd."; }
    revision 2026-06-06 { description "Standalone containers instead of augment (avoids duplicate system container)."; }

    container show {
        config false;
        description "Read-only commands to inspect system, protocol, and network state";

        container firewall {
            config false;
            description "Firewall rules and groups (nftables)";
            container ruleset {
                config false;
                ze:command "ze-show:firewall-ruleset";
                ze:backend "nft";
                description "Show the live firewall ruleset with per-term counters.
Usage: show firewall ruleset <name>. Joins applied desired state with
kernel counters from the nft backend.";
            }
            container group {
                config false;
                ze:command "ze-show:firewall-group";
                ze:backend "nft";
                description "Show members of a firewall address/port group.
Without arguments, lists all known groups. With a name, shows the
set elements. Reads from the last applied config, not the kernel.";
            }
        }

        container system {
            config false;
            description "System-level monitoring and diagnostics";
            container conntrack {
                config false;
                ze:command "ze-show:system-conntrack";
                ze:backend "nft";
                description "Show the kernel connection tracking table.
Returns conntrack entry count, table size, timeouts, and loaded
modules. Requires the nft backend. Check this when you suspect
conntrack table exhaustion is dropping traffic.";
            }
        }
    }
}
