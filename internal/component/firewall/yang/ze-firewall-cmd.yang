module ze-firewall-cmd {
    namespace "urn:ze:firewall:cmd";
    prefix firewallcmd;
    import ze-extensions { prefix ze; }
    description "Firewall show commands: ruleset inspection and address/port group listing.
         Relocated from the central show schema for plugin self-containment.";
    revision 2026-08-29 { description "Declare the value the description spelled in prose, so the model states the grammar and the generated usage line reads it."; }
    revision 2026-06-03 { description "Initial revision: relocated from ze-cli-show-cmd."; }
    revision 2026-06-06 { description "Standalone containers instead of augment (avoids duplicate system container)."; }

    container show {
        config false;
        ze:help "Read-only commands to inspect system, protocol, and network state.";

        container firewall {
            config false;
            description "Ze programs nftables, so what is reported is the state Ze installed. A rule added
                         outside Ze is not managed here and is not shown.";
            ze:help "Firewall rules and groups (nftables).";
            container ruleset {
                config false;
                ze:command "ze-firewall:show-ruleset";
                ze:backend "nft";
                description "Joins applied desired state with kernel counters from
the nft backend.";
                ze:help "Show the live firewall ruleset with per-term counters.";
                leaf name {
                    type string { length "1..64"; }
                    mandatory true;
                    description "The table name as the configuration spells it, without the
ze prefix the backend adds. A name no applied table carries is an error that lists the
tables applied.";
                    ze:help "Firewall table name";
                }
            }
            container group {
                config false;
                ze:command "ze-firewall:show-group";
                ze:backend "nft";
                description "Without arguments, lists all known groups. With a name,
shows the set elements. Reads from the last applied config, not the
kernel.";
                ze:help "Show members of a firewall address/port group.";
            }
        }

        container system {
            config false;
            container conntrack {
                config false;
                ze:command "ze-firewall:show-system-conntrack";
                ze:backend "nft";
                description "Returns conntrack entry count, table size, timeouts,
and loaded modules. Requires the nft backend. Check this when you suspect
conntrack table exhaustion is dropping traffic.";
                ze:help "Show the kernel connection tracking table.";
            }
        }
    }
}
