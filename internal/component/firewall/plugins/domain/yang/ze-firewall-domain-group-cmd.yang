module ze-firewall-domain-group-cmd {
    namespace "urn:ze:firewall-domain-group:cmd";
    prefix fwdgcmd;
    import ze-extensions { prefix ze; }
    description "show, update and clear firewall domain-group command tree.
                 Owned by the firewall-domain plugin so that removing the plugin
                 directory removes these command nodes together with the handlers
                 and the config schema. See ai/rules/plugins.md.";
    revision 2026-09-05 { description "Initial revision."; }

    container show {
        config false;
        ze:help "Read-only commands to inspect system, protocol, and network state.";

        container firewall {
            config false;
            // Repeat the canonical description owned by ze-firewall-cmd.yang
            // verbatim so the command-tree merge does not warn on a mismatch.
            description "Ze programs nftables, so what is reported is the state Ze installed. A rule added
                         outside Ze is not managed here and is not shown.";
            ze:help "Firewall rules and groups (nftables).";

            container domain-group {
                config false;
                ze:command "ze-firewall:show-domain-group-status";
                description "Lists each group with its names, the addresses Ze is enforcing for
                             them, when each name last resolved, and what the last answer said.
                             Read this before a commit to confirm a group has data.";
                ze:help "Show what each configured domain group's DNS names resolve to.";
                leaf name {
                    type string;
                    description "A group from the firewall configuration. A name no group
carries is an error that lists the groups present.";
                    ze:help "Group name; omit to list every group";
                }
            }
        }
    }

    container update {
        config false;

        container firewall {
            config false;
            description "These refresh data the firewall uses and do not edit a rule. A rule an operator
                         wrote stays as written.";
            ze:help "Firewall operational updates.";

            container domain-group {
                config false;
                ze:command "ze-firewall:update-domain-group";
                description "Asks for each name in the group at once rather than waiting for
                             its TTL. A name that fails to resolve keeps the addresses Ze
                             already had for it, and only a name that answers NXDOMAIN empties
                             its own contribution.";
                ze:help "Resolve a domain group's DNS names now and program its set.";
                leaf name {
                    type string;
                    mandatory true;
                    description "A group from the firewall configuration. Every name in that
group is resolved, and a name no group carries is an error that lists the groups present.";
                    ze:help "Domain group name";
                }
            }
        }
    }

    container clear {
        config false;

        container firewall {
            config false;
            // Repeat the canonical description owned by ze-firewall-cmd.yang
            // verbatim so the command-tree merge does not warn on a mismatch.
            description "Clearing removes cached firewall state Ze installed and leaves the configured
                         rules alone, so the next refresh reinstalls them. A rule added outside Ze is
                         untouched.";
            // Repeat the text ze-firewall-irr-cmd.yang carries on this same node
            // verbatim so the command-tree merge does not warn on a mismatch.
            ze:help "Firewall rules and groups (nftables).";

            container domain-group {
                config false;
                ze:command "ze-firewall:clear-domain-group";
                description "Drops the group's addresses from memory and from the persisted
                             cache, then re-applies the firewall tables. Config that still
                             names the group fails to verify until it is resolved again with
                             'update firewall domain-group <name>'.";
                ze:help "Remove the addresses Ze cached for a domain group.";
                leaf name {
                    type string;
                    mandatory true;
                    description "A group from the firewall configuration. The cache entries of
that group's names are purged, and a name no group carries is an error.";
                    ze:help "Domain group name";
                }
            }
        }
    }
}
