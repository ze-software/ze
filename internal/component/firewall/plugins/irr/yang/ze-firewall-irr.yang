module ze-firewall-irr {
    namespace "urn:ze:firewall-irr";
    prefix fwirr;

    import ze-extensions { prefix ze; }
    import ze-types { prefix zt; }
    import ze-firewall-conf { prefix fw; }

    description "IRR-based source/destination address filtering for the firewall.
                 Resolves ASN or AS-SET references to prefix lists via the IRR whois
                 client and populates nftables interval sets. Augments the firewall
                 from-block with source-asn, source-as-set, destination-asn, and
                 destination-as-set leaves, and adds a firewall irr policy container
                 for server, refresh-interval, and peeringdb-url settings.";

    revision 2026-06-17 {
        description "Initial revision";
    }

    augment "/fw:firewall" {
        container irr {
            description "The settings under it reach every IRR reference of the firewall, in a
                         term and on an interface alike. Ze keeps the resolved prefixes in a
                         zefs prefix store that the BGP IRR filter shares, so one query serves
                         both. A commit that names a reference with no cached prefixes is
                         refused.";
            ze:help "IRR policy settings for firewall prefix-list resolution.";

            leaf server {
                type string;
                default "whois.radb.net";
                description "The default is whois.radb.net. Ze adds port 43 when the value names
                             no port, so a host:port value reaches the port you name. One query
                             waits 10 seconds at most, and Ze holds each answer for one hour.";
                ze:help "IRR whois server hostname or host:port.";
            }

            leaf peeringdb-url {
                type string {
                    pattern 'https?://.*';
                }
                default "https://www.peeringdb.com";
                description "The default is https://www.peeringdb.com. Ze adds /api/net?asn=<N>
                             to this value for each query, and holds each answer for one hour.
                             Ze skips TLS verification for the host 127.0.0.1 alone, which is
                             what makes a local test server work.";
                ze:help "Base URL for PeeringDB API queries.
                         Override for testing with a mock server.";
            }

            leaf refresh-interval {
                type uint32 {
                    range "0 | 60..86400";
                }
                default "0";
                units "seconds";
                description "The default 0 disables the automatic refresh, and the
                             operator then runs 'update firewall irr' by hand. A value
                             in 60..86400 starts the periodic refresh. That refresh
                             fails closed: a failed query keeps the last-good cache.";
                ze:help "Seconds between automatic IRR re-queries.";
            }

            list interface {
                key "name";
                description "Ze drops a packet that arrives on this interface when its
                             source address is not in the IRR-resolved prefixes of the
                             AS-SET.";
                ze:help "Per-interface AS-SET binding for ingress source validation.";

                leaf name {
                    type string {
                        length "1..15";
                        pattern '[a-zA-Z0-9._-]+';
                    }
                    description "Ze matches the input interface by this name in the nftables
                                 rule, so a name no interface carries filters nothing. The
                                 15-character limit is the kernel limit on an interface name. A
                                 binding whose AS-SET resolved to no prefix produces no rule at
                                 all, and Ze logs a warning that names the interface.";
                    ze:help "Interface name (e.g. eth1, bond0.100).
                             Must match the kernel interface name exactly.";
                }

                leaf source-as-set {
                    type string {
                        length "1..255";
                        pattern '[A-Za-z0-9:._-]+';
                    }
                    mandatory true;
                    description "The prefixes the IRR resolves for this AS-SET form the
                                 allowed source-address set of the interface. The match
                                 needs cached prefix data. A config commit is refused
                                 when no cached data exists.";
                    ze:help "AS-SET whose IRR-resolved prefixes are the allowed source addresses.";
                }
            }
        }
    }

    augment "/fw:firewall/fw:table/fw:chain/fw:term/fw:from" {
        leaf source-asn {
            type zt:asn {
                range "1..4294967294";
            }
            description "The match needs cached prefix data, so run 'update firewall
                         irr asn <N>' first. A config commit is refused when no cached
                         data exists.";
            ze:help "Match the source address against the IRR-resolved prefixes of this ASN.";
        }

        leaf source-as-set {
            type string {
                length "1..255";
                pattern '[A-Za-z0-9:._-]+';
            }
            description "The match needs cached prefix data, so run 'update firewall
                         irr as-set <name>' first. A config commit is refused when no
                         cached data exists.";
            ze:help "Match the source address against the IRR-resolved prefixes of this AS-SET.";
        }

        leaf destination-asn {
            type zt:asn {
                range "1..4294967294";
            }
            description "The cache rule is the one source-asn states. The match needs
                         cached prefix data, so run 'update firewall irr asn <N>'
                         first. A config commit is refused when no cached data
                         exists.";
            ze:help "Match the destination address against the IRR-resolved prefixes of this ASN.";
        }

        leaf destination-as-set {
            type string {
                length "1..255";
                pattern '[A-Za-z0-9:._-]+';
            }
            description "The cache rule is the one source-as-set states. The match
                         needs cached prefix data, so run 'update firewall irr as-set
                         <name>' first. A config commit is refused when no cached data
                         exists.";
            ze:help "Match the destination address against the IRR-resolved prefixes of this AS-SET.";

        }
    }
}
