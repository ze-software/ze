module ze-iface-conf {
    namespace "urn:ze:iface:conf";
    prefix iface;

    import ze-types { prefix zt; }
    import ze-extensions { prefix ze; }

    description "Network interface configuration for Ze";

    revision 2026-01-01 {
        description "Initial revision";
    }

    grouping interface-common {
        description "Interface properties common to all kinds (L2 and L3)";

        leaf description {
            type string {
                length "0..255";
            }
            description "Interface description";
        }

        leaf mtu {
            type uint16 {
                range "68..16000";
            }
            default 1500;
            description "Maximum transmission unit";
        }

        leaf os-name {
            ze:hidden "true";
            type string;
            description "Original OS interface name at discovery time";
        }

        leaf disable {
            type empty;
            description "Administratively disable this interface";
        }
    }

    grouping interface-l2 {
        description "Interface properties for kinds that expose a MAC
                     address at the list level: ethernet, dummy, veth,
                     bridge. Tunnel L2 kinds (gretap, ip6gretap) carry
                     mac-address inside their per-case containers instead.
                     L3-only kinds with no MAC (e.g. wireguard, L3 tunnels)
                     use interface-common directly.";

        uses interface-common;

        leaf mac-address {
            type string {
                pattern '[0-9a-fA-F]{2}(:[0-9a-fA-F]{2}){5}';
            }
            ze:validate "mac-address";
            description "Hardware MAC address";
        }

        container offload {
            description "Network offload and packet steering features.
                         Applied directly via kernel ioctl (the ethtool
                         SIOCETHTOOL interface) or sysfs writes after the
                         interface is created. The ethtool(8) CLI program is
                         NOT required; ze talks to the kernel directly.
                         Boolean leaves: true = explicitly enable the feature,
                         false = explicitly disable, absent = preserve whatever
                         the OS default is (no kernel call is made).
                         Offload availability depends on the NIC driver and
                         kernel version; unsupported features are logged as
                         warnings and do not block the config commit.";

            leaf gro {
                type boolean;
                description "Generic Receive Offload. Aggregates small incoming
                             packets into larger ones before passing them up the
                             network stack, reducing per-packet CPU overhead.
                             Software-based (works on all NIC types including
                             veth and dummy). Applied via kernel ioctl
                             (ETHTOOL_SGRO). Equivalent to: ethtool -K <dev>
                             gro on|off.";
            }

            leaf gso {
                type boolean;
                description "Generic Segmentation Offload. Delays segmentation
                             of large outgoing packets until just before the NIC
                             driver transmit path, reducing CPU work in the upper
                             stack. Software-based counterpart of TSO. Applied
                             via kernel ioctl (ETHTOOL_SGSO). Equivalent to:
                             ethtool -K <dev> gso on|off.";
            }

            leaf sg {
                type boolean;
                description "Scatter-Gather I/O. Allows the NIC to assemble a
                             single frame from multiple non-contiguous memory
                             buffers, avoiding data copies. Required by TSO and
                             GSO on most drivers. Applied via kernel ioctl
                             (ETHTOOL_SSG). Equivalent to: ethtool -K <dev>
                             sg on|off.";
            }

            leaf tso {
                type boolean;
                description "TCP Segmentation Offload. Offloads TCP segmentation
                             to the NIC hardware, allowing the kernel to hand off
                             large (up to 64 KB) TCP segments that the NIC splits
                             into MTU-sized frames on the wire. Requires NIC
                             hardware support. Disable when passing traffic to
                             VPP or virtual switches that cannot handle oversized
                             frames. Applied via kernel ioctl (ETHTOOL_STSO).
                             Equivalent to: ethtool -K <dev> tso on|off.";
            }

            leaf lro {
                type boolean;
                description "Large Receive Offload. Hardware-based counterpart of
                             GRO: the NIC coalesces incoming TCP segments before
                             DMA. Can break forwarding and bridging because the
                             coalesced frame no longer matches the original wire
                             format. Disable on routers or bridges that forward
                             traffic between interfaces. Applied via kernel ioctl
                             (ETHTOOL_SLRO). Equivalent to: ethtool -K <dev>
                             lro on|off.";
            }

            leaf hw-tc-offload {
                type boolean;
                description "Hardware Traffic Control Offload. Enables the NIC to
                             execute TC flower / u32 filter rules in hardware,
                             bypassing kernel processing for matched flows.
                             Requires NIC firmware support (common on mlx5, bnxt,
                             nfp). Applied via kernel ioctl (ETHTOOL_SFEATURES).
                             Equivalent to: ethtool -K <dev> hw-tc-offload
                             on|off.";
            }

            leaf rps {
                type boolean;
                description "Receive Packet Steering. Software-based distribution
                             of incoming packets across multiple CPUs by hashing
                             the packet header and steering to a target CPU receive
                             queue. Useful when the NIC has fewer hardware RSS
                             queues than available CPUs. When enabled, ze writes
                             a bitmask covering all online CPUs to each rx queue
                             sysfs entry (/sys/class/net/<dev>/queues/rx-*/
                             rps_cpus). When disabled, ze writes 0 to each entry.
                             Not an ethtool feature; uses sysfs directly.";
            }

            leaf rfs {
                type boolean;
                description "Receive Flow Steering. Extension of RPS that steers
                             incoming packets to the CPU where the application
                             consuming that flow is running, improving cache
                             locality and reducing cross-CPU cache bounces. When
                             enabled, ze sets /proc/sys/net/core/
                             rps_sock_flow_entries to 32768 and distributes
                             per-queue rps_flow_cnt evenly across rx queues.
                             RPS should also be enabled for RFS to be effective.
                             Not an ethtool feature; uses sysfs directly.";
            }
        }
    }

    grouping interface-unit {
        description "Logical interface unit properties";

        list unit {
            key "name";
            description "Logical interface unit";

            leaf name {
                type zt:node-name;
                description "Unit name (lowercase alphanumeric and hyphens)";
            }

            leaf vlan-id {
                type uint16 {
                    range "1..4094";
                }
                description "VLAN identifier";
            }

            leaf description {
                type string {
                    length "0..255";
                }
                description "Unit description";
            }

            leaf disable {
                type empty;
                description "Administratively disable this unit";
            }

            leaf route-priority {
                type uint32 {
                    range "0..4294966271";
                }
                default 0;
                description "Route metric for default routes installed via DHCP on
                             this unit. Lower values are preferred. On link-down,
                             the metric is increased by 1024 to deprioritize the
                             interface. 0 = kernel default.";
            }

            leaf vrf {
                type string;
                description "VRF membership";
            }

            leaf-list sysctl-profile {
                type zt:node-name;
                max-elements 10;
                ze:syntax "bracket";
                description "Named sysctl profiles to apply to this unit.
                             Built-in: dsr, router, hardened, multihomed, proxy.
                             User-defined profiles from sysctl { profile ... } config.
                             Applied in order; last wins on key overlap.";
            }

            container ipv4 {
                description "IPv4 protocol settings";

                leaf-list address {
                    type string {
                        pattern '[0-9]{1,3}\.[0-9]{1,3}\.[0-9]{1,3}\.[0-9]{1,3}/[0-9]{1,2}';
                    }
                    ze:syntax "bracket";
                    description "IPv4 addresses in CIDR notation (e.g., 10.0.0.1/24)";
                }

                leaf forwarding {
                    type boolean;
                    description "Enable IPv4 forwarding";
                }

                leaf arp-filter {
                    type boolean;
                    description "Enable ARP filtering";
                }

                leaf arp-accept {
                    type boolean;
                    description "Accept unsolicited ARP replies";
                }

                leaf proxy-arp {
                    type boolean;
                    description "Enable proxy ARP";
                }

                leaf arp-announce {
                    type uint8 {
                        range "0..2";
                    }
                    default 0;
                    description "ARP announce level: 0=any, 1=prefer subnet, 2=best only";
                }

                leaf arp-ignore {
                    type uint8 {
                        range "0..2";
                    }
                    default 0;
                    description "ARP ignore level: 0=reply any, 1=reply only if target on incoming iface, 2=plus sender subnet check";
                }

                leaf rpf-check {
                    type enumeration {
                        enum disable;
                        enum strict;
                        enum loose;
                    }
                    description "Reverse path filtering mode";
                }

                container dhcp {
                    ze:backend "netlink";
                    description "DHCPv4 client configuration";

                    leaf enabled {
                        type boolean;
                        default false;
                        description "Enable DHCPv4 client";
                    }

                    leaf client-id {
                        type string;
                        description "Client identifier";
                    }

                    leaf hostname {
                        type string;
                        description "Hostname in DHCP requests";
                    }
                }
            }

            container ipv6 {
                description "IPv6 protocol settings";

                leaf-list address {
                    type string {
                        pattern '[0-9a-fA-F:]{2,39}/[0-9]{1,3}';
                    }
                    ze:syntax "bracket";
                    description "IPv6 addresses in CIDR notation (e.g., fd00::1/64)";
                }

                leaf autoconf {
                    type boolean;
                    description "Enable IPv6 stateless autoconfiguration";
                }

                leaf accept-ra {
                    type uint8 {
                        range "0..2";
                    }
                    default 0;
                    description "Accept RA level: 0=disable, 1=if not forwarding, 2=even if forwarding";
                }

                leaf forwarding {
                    type boolean;
                    description "Enable IPv6 forwarding";
                }

                leaf rpf-check {
                    type enumeration {
                        enum disable;
                        enum strict;
                        enum loose;
                    }
                    description "Reverse path filtering mode (VPP data plane only on IPv6)";
                }

                container dhcpv6 {
                    ze:backend "netlink";
                    description "DHCPv6 client configuration";

                    leaf enabled {
                        type boolean;
                        default false;
                        description "Enable DHCPv6 client";
                    }

                    container pd {
                        description "Prefix delegation";

                        leaf length {
                            type uint8 {
                                range "48..64";
                            }
                            description "Requested prefix length";
                        }
                    }

                    leaf duid {
                        type string;
                        description "DUID override";
                    }
                }
            }

            container mirror {
                ze:os "linux";
                ze:backend "netlink";
                description "Traffic mirroring";

                leaf ingress {
                    type string;
                    description "Mirror ingress traffic to this interface";
                }

                leaf egress {
                    type string;
                    description "Mirror egress traffic to this interface";
                }
            }

            container mpls {
                ze:os "linux";
                description "MPLS forwarding on this interface (RFC 3031 LSR).";

                leaf enable {
                    type boolean;
                    default false;
                    description "Enable MPLS label input on this interface (net.mpls.conf.<iface>.input). The global label table size is set via net.mpls.platform_labels.";
                }
            }
        }
    }

    grouping tunnel-v4-endpoints {
        description "IPv4 underlay endpoints for a tunnel.";

        container local {
            description "Local IPv4 endpoint or source interface (one of ip or interface)";

            leaf ip {
                type zt:ipv4-address;
                description "Local IPv4 endpoint";
            }

            leaf interface {
                type string;
                description "Local interface to take the source address from";
            }
        }

        container remote {
            description "Remote IPv4 endpoint";

            leaf ip {
                type zt:ipv4-address;
                mandatory true;
                description "Remote IPv4 endpoint";
            }
        }
    }

    grouping tunnel-v6-endpoints {
        description "IPv6 underlay endpoints for a tunnel.";

        container local {
            description "Local IPv6 endpoint or source interface (one of ip or interface)";

            leaf ip {
                type zt:ipv6-address;
                description "Local IPv6 endpoint";
            }

            leaf interface {
                type string;
                description "Local interface to take the source address from";
            }
        }

        container remote {
            description "Remote IPv6 endpoint";

            leaf ip {
                type zt:ipv6-address;
                mandatory true;
                description "Remote IPv6 endpoint";
            }
        }
    }

    container interface {
        description "Network interface configuration.

                     Interface names MUST NOT be one of the CLI reserved
                     keywords: brief, scan, type, errors, counters. These
                     collide with the `show interface` / `clear interface`
                     command grammar (e.g. `show interface counters` would
                     be ambiguous if an interface were literally named
                     `counters`). Reserved names are rejected by
                     iface.ValidateIfaceName at apply time with a clear
                     error; the kernel does not enforce this on its own.";

        leaf backend {
            type string;
            default "netlink";
            description "Interface management backend (e.g., netlink, networkd)";
        }

        leaf dhcp-auto {
            type boolean;
            default false;
            description "Auto-discover first ethernet interface and run DHCP on it. Used when the interface name is not known at config time (e.g., gokrazy appliance). Ignored if any explicit DHCP config exists.";
        }

        list ethernet {
            key "name";
            unique "mac-address";
            ze:required "mac-address";
            description "Ethernet interface";

            leaf name {
                type string;
                description "Interface name";
            }

            uses interface-l2;
            uses interface-unit;
        }

        list dummy {
            key "name";
            description "Dummy interface";

            leaf name {
                type string;
                description "Interface name";
            }

            uses interface-l2;
            uses interface-unit;
        }

        list veth {
            key "name";
            unique "mac-address";
            ze:required "mac-address";
            ze:backend "netlink";
            description "Virtual ethernet pair interface";

            leaf name {
                type string;
                description "Interface name";
            }

            leaf peer {
                type string;
                description "Veth peer name";
            }

            uses interface-l2;
            uses interface-unit;
        }

        list bridge {
            key "name";
            unique "mac-address";
            ze:required "mac-address";
            ze:backend "netlink";
            description "Bridge interface";

            leaf name {
                type string;
                description "Interface name";
            }

            leaf stp {
                ze:os "linux";
                type boolean;
                default false;
                description "Enable Spanning Tree Protocol";
            }

            leaf-list member {
                ze:os "linux";
                type string;
                ze:syntax "bracket";
                description "Member port interface names";
            }

            uses interface-l2;
            uses interface-unit;
        }

        list tunnel {
            key "name";
            ze:backend "netlink";
            description "Tunnel interface (GRE/GRETAP/IPIP/SIT/IP6TNL families).
                         Encapsulation kind is selected by the choice below; each
                         case carries only the leaves valid for that kind.
                         The local/remote endpoint pattern matches bgp peer
                         connection { local { ip ... } remote { ip ... } }.";

            leaf name {
                type string;
                description "Interface name (free-form, validated by iface naming rules)";
            }

            container encapsulation {
                description "Tunnel encapsulation kind and per-kind parameters";

                choice kind {
                    mandatory true;
                    description "Encapsulation discriminator. Invalid combinations
                                 (e.g. key on ipip) are unrepresentable in the schema.";

                    case gre {
                        description "GRE over IPv4 (RFC 2784, key extension RFC 2890). L3.";
                        container gre {
                            description "GRE-over-IPv4 parameters";
                            uses tunnel-v4-endpoints;

                            leaf key {
                                type uint32;
                                description "32-bit GRE key (RFC 2890). Symmetric: same
                                             value used for input and output";
                            }

                            leaf ttl {
                                type uint8;
                                default 0;
                                description "Outer-header TTL. 0 = inherit from inner";
                            }

                            leaf tos {
                                type uint8;
                                default 0;
                                description "Outer-header Type of Service. 0 = inherit";
                            }

                            leaf no-pmtu-discovery {
                                type empty;
                                description "Disable Path MTU Discovery on the outer header";
                            }
                        }
                    }

                    case gretap {
                        description "GRE over IPv4, L2 (Ethernet over GRE, bridgeable). RFC 2784.";
                        container gretap {
                            description "GRETAP-over-IPv4 parameters";
                            uses tunnel-v4-endpoints;

                            leaf key {
                                type uint32;
                                description "32-bit GRE key (RFC 2890)";
                            }

                            leaf ttl {
                                type uint8;
                                default 0;
                                description "Outer-header TTL. 0 = inherit";
                            }

                            leaf tos {
                                type uint8;
                                default 0;
                                description "Outer-header Type of Service. 0 = inherit";
                            }

                            leaf no-pmtu-discovery {
                                type empty;
                                description "Disable Path MTU Discovery on the outer header";
                            }

                            leaf mac-address {
                                type string {
                                    pattern '[0-9a-fA-F]{2}(:[0-9a-fA-F]{2}){5}';
                                }
                                ze:validate "mac-address";
                                description "Hardware MAC address (L2 tunnel kinds only)";
                            }
                        }
                    }

                    case ip6gre {
                        description "GRE over IPv6 (RFC 2784, key extension RFC 2890). L3.";
                        container ip6gre {
                            description "GRE-over-IPv6 parameters";
                            uses tunnel-v6-endpoints;

                            leaf key {
                                type uint32;
                                description "32-bit GRE key (RFC 2890)";
                            }

                            leaf hoplimit {
                                type uint8;
                                default 64;
                                description "Outer IPv6 hop limit (RFC 2473 Section 6.3)";
                            }

                            leaf tclass {
                                type uint8;
                                default 0;
                                description "Outer IPv6 traffic class (RFC 2473 Section 6.4)";
                            }
                        }
                    }

                    case ip6gretap {
                        description "GRE over IPv6, L2 (Ethernet over GRE bridgeable). RFC 2784.";
                        container ip6gretap {
                            description "GRETAP-over-IPv6 parameters";
                            uses tunnel-v6-endpoints;

                            leaf key {
                                type uint32;
                                description "32-bit GRE key (RFC 2890)";
                            }

                            leaf hoplimit {
                                type uint8;
                                default 64;
                                description "Outer IPv6 hop limit";
                            }

                            leaf tclass {
                                type uint8;
                                default 0;
                                description "Outer IPv6 traffic class";
                            }

                            leaf mac-address {
                                type string {
                                    pattern '[0-9a-fA-F]{2}(:[0-9a-fA-F]{2}){5}';
                                }
                                ze:validate "mac-address";
                                description "Hardware MAC address (L2 tunnel kinds only)";
                            }
                        }
                    }

                    case ipip {
                        description "IPv4 in IPv4 (RFC 2003). No GRE header, no key. L3.";
                        container ipip {
                            description "IPIP parameters";
                            uses tunnel-v4-endpoints;

                            leaf ttl {
                                type uint8;
                                default 0;
                                description "Outer-header TTL. 0 = inherit";
                            }

                            leaf tos {
                                type uint8;
                                default 0;
                                description "Outer-header Type of Service. 0 = inherit";
                            }

                            leaf no-pmtu-discovery {
                                type empty;
                                description "Disable Path MTU Discovery on the outer header";
                            }
                        }
                    }

                    case sit {
                        description "IPv6 in IPv4 (6in4, RFC 4213 Section 3). L3.";
                        container sit {
                            description "SIT (6in4) parameters";
                            uses tunnel-v4-endpoints;

                            leaf ttl {
                                type uint8;
                                default 0;
                                description "Outer-header TTL. 0 = inherit";
                            }

                            leaf tos {
                                type uint8;
                                default 0;
                                description "Outer-header Type of Service. 0 = inherit";
                            }

                            leaf no-pmtu-discovery {
                                type empty;
                                description "Disable Path MTU Discovery on the outer header";
                            }
                        }
                    }

                    case ip6tnl {
                        description "IPv6 in IPv6 (RFC 2473). Also covers ip6ip6. L3.";
                        container ip6tnl {
                            description "IP6TNL parameters";
                            uses tunnel-v6-endpoints;

                            leaf hoplimit {
                                type uint8;
                                default 64;
                                description "Outer IPv6 hop limit (RFC 2473 Section 6.3)";
                            }

                            leaf tclass {
                                type uint8;
                                default 0;
                                description "Outer IPv6 traffic class (RFC 2473 Section 6.4)";
                            }

                            leaf encaplimit {
                                type uint8;
                                default 4;
                                description "Tunnel encapsulation limit (RFC 2473 Section 4.1.1)";
                            }
                        }
                    }

                    case ipip6 {
                        description "IPv4 in IPv6 (RFC 2473 with Next Header = 4). L3.
                                     Implemented via the ip6tnl Linux kind with Proto=IPPROTO_IPIP.";
                        container ipip6 {
                            description "IPIP6 parameters";
                            uses tunnel-v6-endpoints;

                            leaf hoplimit {
                                type uint8;
                                default 64;
                                description "Outer IPv6 hop limit";
                            }

                            leaf tclass {
                                type uint8;
                                default 0;
                                description "Outer IPv6 traffic class";
                            }

                            leaf encaplimit {
                                type uint8;
                                default 4;
                                description "Tunnel encapsulation limit";
                            }
                        }
                    }
                }
            }

            uses interface-common;
            uses interface-unit;
        }

        list wireguard {
            key "name";
            ze:listener;
            ze:backend "netlink";
            description "WireGuard interface. Declarative config: interface-level
                         listen-port, fwmark, private-key, and a nested peer list
                         with public-key, endpoint, allowed-ips, preshared-key,
                         and persistent-keepalive. L3 kind with no MAC address
                         (uses interface-common rather than interface-l2).
                         Reconciliation is in-place per peer via wgctrl
                         ConfigureDevice; adding, removing, or rekeying a peer
                         does not disturb the netdev or any other peer.";

            leaf name {
                type string;
                description "Interface name (free-form, validated by iface naming rules)";
            }

            leaf listen-port {
                type zt:port;
                description "UDP port WireGuard binds on 0.0.0.0 and :: for
                             peer handshake and data traffic. If unset the
                             kernel chooses an ephemeral port on the first
                             outbound handshake.";
            }

            leaf fwmark {
                type uint32;
                default 0;
                description "Firewall mark applied to outgoing encapsulated
                             packets for policy routing. 0 means unset.";
            }

            leaf private-key {
                mandatory true;
                type string;
                ze:sensitive;
                description "Base64-encoded 32-byte Curve25519 private key.
                             Stored $9$-encoded on disk via the standard ze
                             sensitive-leaf pattern; decoded to plaintext
                             base64 at parse time. ze config show / dump
                             always emits the $9$ form, never the plaintext.
                             Obfuscation only (not encryption) -- protect the
                             config file at filesystem level (chmod 600) just
                             like BGP MD5 passwords.";
            }

            list peer {
                key "name";
                description "WireGuard peer";

                leaf name {
                    type string;
                    description "Peer name (free-form, used as list key)";
                }

                leaf public-key {
                    type string;
                    mandatory true;
                    description "Base64-encoded 32-byte Curve25519 peer public key";
                }

                leaf preshared-key {
                    type string;
                    ze:sensitive;
                    description "Optional base64-encoded 32-byte symmetric
                                 preshared key mixed into the handshake for
                                 post-quantum resistance. Stored $9$-encoded
                                 on disk, same pattern as private-key.";
                }

                container endpoint {
                    description "Remote UDP endpoint for this peer. Both leaves
                                 are required together; the kernel uses this
                                 address on the first outbound handshake and
                                 updates it on every inbound handshake from
                                 a new source address.";

                    leaf ip {
                        type zt:ip-address;
                        description "Remote IPv4 or IPv6 address (numeric, not
                                     a hostname -- DNS resolution is not performed)";
                    }

                    leaf port {
                        type zt:port;
                        description "Remote UDP port";
                    }
                }

                leaf-list allowed-ips {
                    type string {
                        pattern '[0-9a-fA-F:][0-9a-fA-F:.]*(/[0-9]{1,3})?';
                    }
                    ze:syntax "bracket";
                    description "CIDR prefixes routed into the tunnel for this
                                 peer. Inbound packets from this peer must have
                                 a source address inside one of these prefixes
                                 (cryptokey routing).";
                }

                leaf persistent-keepalive {
                    type uint16 {
                        range "0..65535";
                    }
                    default 0;
                    description "Seconds between unsolicited keepalive packets
                                 to maintain NAT state. 0 disables keepalives.
                                 Typical value is 25.";
                }

                leaf disable {
                    type empty;
                    description "Administratively disable this peer. The peer
                                 is removed from the kernel peer set on reload
                                 but stays in the config.";
                }
            }

            uses interface-common;
            uses interface-unit;
        }

        list xfrm {
            key "name";
            ze:os "linux";
            ze:backend "netlink";
            description "XFRM interface (Linux 4.19+). Route-based IPsec: traffic
                         routed into this interface is encrypted/decrypted by the
                         kernel XFRM subsystem. The if-id binds security associations
                         to the interface. L3 kind with no MAC address.";

            leaf name {
                type string;
                description "Interface name (free-form, validated by iface naming rules)";
            }

            leaf if-id {
                mandatory true;
                type uint32 {
                    range "1..4294967295";
                }
                description "XFRM interface identifier. Binds this interface to
                             XFRM security associations that carry the same if_id.
                             Must be non-zero (0 means unset in the kernel).";
            }

            leaf dev {
                type string;
                description "Optional parent device name. When set, the XFRM interface
                             is bound to this physical device. When omitted, the
                             interface is unbound and uses the routing table to select
                             the underlay.";
            }

            uses interface-common;
            uses interface-unit;
        }

        list pppoe-client {
            key "name";
            ze:os "linux";
            ze:backend "netlink";
            description "PPPoE client interface (RFC 2516). Dials an access
                         concentrator over a physical Ethernet interface,
                         negotiates LCP/auth/IPCP, and presents the resulting
                         PPP session as a routable interface with server-
                         assigned addresses. The kernel pppN interface is
                         created dynamically; the name leaf is a config key
                         only (the OS interface name is pppN).";

            leaf name {
                type string;
                description "Config-level interface name (e.g. pppoe0)";
            }

            leaf source-interface {
                mandatory true;
                type string;
                description "Physical Ethernet interface for PPPoE discovery
                             (e.g. eth2). Must exist and be admin-up.";
            }

            container authentication {
                description "PPPoE authentication credentials (PAP or CHAP)";

                leaf username {
                    mandatory true;
                    type string {
                        length "1..255";
                    }
                    description "Authentication username sent to the AC";
                }

                leaf password {
                    mandatory true;
                    type string {
                        length "1..255";
                    }
                    ze:sensitive;
                    description "Authentication password. Stored $9$-encoded
                                 on disk via the standard ze sensitive-leaf
                                 pattern.";
                }
            }

            leaf service-name {
                type string {
                    length "0..255";
                }
                description "Desired PPPoE service name. Empty or absent
                             means accept any service (RFC 2516 Section 5.1).";
            }

            leaf ac-name {
                type string {
                    length "0..255";
                }
                description "Desired access concentrator name. When set,
                             only PADO frames from this AC are accepted.
                             Empty or absent means accept any AC.";
            }

            leaf no-default-route {
                type empty;
                description "Do not install a default route via the PPP
                             interface. When absent (default), a default
                             route is installed after IPCP completes.";
            }

            uses interface-common;
        }

        container loopback {
            description "Loopback interface";

            uses interface-unit;
        }

        container monitor {
            description "Interface monitoring settings";

            leaf loopback {
                type boolean;
                default false;
                description "Monitor loopback interface";
            }
        }
    }
}
