module ze-iface-cmd {
    namespace "urn:ze:iface:cmd";
    prefix ifacecmd;
    import ze-extensions { prefix ze; }
    description "Create, configure, and manage network interfaces";
    revision 2026-06-04 { description "Verb-first grammar: create/delete/request interface"; }

    container create {
        config false;
        description "Create new resources";

        container interface {
            config false;
            description "Create interfaces, units, and addresses";

            container dummy {
                config false;
                ze:command "ze-iface:interface-create-dummy";
                ze:backend "netlink";
                ze:ensure-exists "ze-iface:interface-delete";
                description "Create a dummy (loopback-style) interface.
Usage: create interface dummy <name>.";
                leaf name { type string; mandatory true; description "Interface name"; }

                container unit {
                    config false;
                    ze:command "ze-iface:interface-unit-add";
                    ze:backend "netlink";
                    description "Create a dummy interface (if needed) and add a VLAN sub-interface.
Usage: create interface dummy <name> unit <vid>.";
                    leaf name { type string; mandatory true; description "Parent interface name"; }
                }

                container address {
                    config false;
                    ze:command "ze-iface:interface-addr-add";
                    ze:backend "netlink";
                    description "Create a dummy interface (if needed) and add an IP address.
Usage: create interface dummy <name> address <prefix>.";
                    leaf name { type string; mandatory true; description "Interface name"; }
                }
            }

            container veth {
                config false;
                ze:command "ze-iface:interface-create-veth";
                ze:backend "netlink";
                description "Create a veth pair (two linked virtual Ethernet interfaces).
Usage: create interface veth <name> <peer>.";
                leaf name { type string; mandatory true; description "Interface name"; }
            }

            container bridge {
                config false;
                ze:command "ze-iface:interface-create-bridge";
                ze:backend "netlink";
                ze:ensure-exists "ze-iface:interface-delete";
                description "Create a Linux bridge for L2 forwarding.
Usage: create interface bridge <name>.";
                leaf name { type string; mandatory true; description "Interface name"; }

                container unit {
                    config false;
                    ze:command "ze-iface:interface-unit-add";
                    ze:backend "netlink";
                    description "Create a bridge (if needed) and add a VLAN sub-interface.
Usage: create interface bridge <name> unit <vid>.";
                    leaf name { type string; mandatory true; description "Parent interface name"; }
                }

                container address {
                    config false;
                    ze:command "ze-iface:interface-addr-add";
                    ze:backend "netlink";
                    description "Create a bridge (if needed) and add an IP address.
Usage: create interface bridge <name> address <prefix>.";
                    leaf name { type string; mandatory true; description "Interface name"; }
                }
            }

            container unit {
                config false;
                ze:command "ze-iface:interface-unit-add";
                description "Add a VLAN sub-interface (802.1Q tagged).
Usage: create interface <parent> unit <vid>. Parent must already exist.";
                leaf name { type string; mandatory true; description "Parent interface name"; }
            }

            container address {
                config false;
                ze:command "ze-iface:interface-addr-add";
                description "Add an IP address to an interface.
Usage: create interface <name> address <prefix>. Interface must already exist.";
                leaf name { type string; mandatory true; description "Interface name"; }
            }
        }
    }

    container delete {
        config false;
        description "Delete resources";

        container interface {
            config false;
            ze:command "ze-iface:interface-delete";
            description "Delete an interface from the kernel.
Usage: delete interface <name>.";
            leaf name { type string; mandatory true; description "Interface name"; }

            container unit {
                config false;
                ze:command "ze-iface:interface-unit-del";
                description "Remove a VLAN sub-interface.
Usage: delete interface <name> unit.";
                leaf name { type string; mandatory true; description "Sub-interface name (e.g. eth0.100)"; }
            }

            container address {
                config false;
                ze:command "ze-iface:interface-addr-del";
                description "Remove an IP address from an interface.
Usage: delete interface <name> address <prefix>.";
                leaf name { type string; mandatory true; description "Interface name"; }
            }
        }
    }

    container request {
        config false;
        description "Operational actions on network interfaces";

        container interface {
            config false;
            description "Interface operational state";

            container up {
                config false;
                ze:command "ze-iface:interface-up";
                description "Bring an interface up.
Usage: request interface <name> up.";
                leaf name { type string; mandatory true; description "Interface name"; }
            }

            container down {
                config false;
                ze:command "ze-iface:interface-down";
                description "Shut down an interface.
Usage: request interface <name> down.";
                leaf name { type string; mandatory true; description "Interface name"; }
            }

            container mtu {
                config false;
                ze:command "ze-iface:interface-mtu";
                description "Set the MTU on an interface.
Usage: request interface <name> mtu <bytes>. Range: 68 to 65535.";
                leaf name { type string; mandatory true; description "Interface name"; }
            }

            container mac {
                config false;
                ze:command "ze-iface:interface-mac";
                description "Set the MAC address on an interface.
Usage: request interface <name> mac <aa:bb:cc:dd:ee:ff>.";
                leaf name { type string; mandatory true; description "Interface name"; }
            }

            container migrate {
                config false;
                ze:command "ze-iface:interface-migrate";
                description "Move IP addresses between interfaces with minimal downtime.
Uses --from, --to, --address flags. Adds addresses to the target
before removing them from the source (make-before-break).";
            }
        }
    }
}
