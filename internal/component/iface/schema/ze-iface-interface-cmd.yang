module ze-iface-interface-cmd {
    namespace "urn:ze:iface:interface:cmd";
    prefix ifaceifcmd;
    import ze-extensions { prefix ze; }
    description "show interface family (interface, brief, scan, type, errors, rate, name detail/counters) and monitor interface rate. Owned by the iface component because every handler reads interface state through the iface backend (iface.ListInterfaces / GetInterface / DiscoverInterfaces / GetRate). Container-merges onto the show and monitor verb roots. See ai/rules/plugin-self-containment.md.";
    revision 2026-06-03 { description "Relocated the show interface family and monitor interface rate out of the central show and monitor schemas into the iface component (plugin self-containment)."; }

    container show {
        config false;
        description "Read-only commands to inspect system, protocol, and network state";

        container interface {
            config false;
            ze:command "ze-show:interface";
            description "Show network interfaces on this box.
Without arguments, returns all interfaces with full detail.
Subcommands: brief, type <t>, errors, rate [<name>], name <name> detail,
name <name> counters.";

            container brief {
                config false;
                ze:command "ze-show:interface";
                description "One-line summary per interface: name, state, IP, and MTU.
Quick way to see what is up and what addresses are assigned.";
            }

            container scan {
                config false;
                ze:command "ze-show:interface-scan";
                description "Discover and classify all OS interfaces.
Returns name, Ze type (ethernet, bridge, vxlan, etc.), and MAC for
each interface found. Pipe to table, yaml, or json for different
views. Useful during initial setup to see what the box has.";
            }

            container type {
                config false;
                ze:command "ze-show:interface";
                description "Show only interfaces of a given type.
Usage: show interface type <type>. Types include ethernet, bridge,
vxlan, wireguard, tunnel, bond, and more. If you pick an invalid
type, the error lists all valid ones.";
            }

            container errors {
                config false;
                ze:command "ze-show:interface";
                description "Show interfaces that have errors or drops.
Filters to only interfaces with non-zero Rx/Tx error or drop
counters. Quick way to find troubled links.";
            }

            container rate {
                config false;
                ze:command "ze-show:interface";
                description "Show per-second traffic rates on your interfaces.
Returns rx/tx bytes and packets per second. Pass an interface name
to narrow the output. Requires the rate tracker. For continuous
monitoring, use 'monitor interface rate' instead.";
            }

            container name {
                config false;
                description "Select one interface by name.";

                container detail {
                    config false;
                    ze:command "ze-show:interface-detail";
                    description "Show full detail for one interface.
Usage: show interface name <name> detail.";
                    leaf name {
                        type string;
                        mandatory true;
                        description "Interface name";
                    }
                }

                container counters {
                    config false;
                    ze:command "ze-show:interface-counters";
                    description "Show counters for one interface.
Usage: show interface name <name> counters.";
                    leaf name {
                        type string;
                        mandatory true;
                        description "Interface name";
                    }
                }
            }
        }
    }

    container monitor {
        config false;
        description "Continuous monitoring commands (Ctrl-C to stop)";

        container interface {
            config false;
            description "Interface traffic monitoring";

            container rate {
                config false;
                ze:command "ze-monitor:interface-rate";
                ze:task-support required;
                description "Stream per-second traffic rates for your interfaces.
Shows rx/tx bytes and packets per second, updating every second.
Optionally pass an interface name to watch just one link.";
            }
        }
    }
}
