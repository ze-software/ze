module ze-iface-monitor-cmd {
    namespace "urn:ze:iface:monitor:cmd";
    prefix ifacemonitorcmd;
    import ze-extensions { prefix ze; }
    // The handler streams kernel netlink events through the iface backend:
    // routes, links, and addresses. See ai/rules/plugin-self-containment.md.
    description "The monitor system netlink command tree, owned by the iface component.";
    revision 2026-06-06 { description "Relocated monitor system netlink out of the central monitor schema (plugin self-containment)."; }

    container monitor {
        config false;
        ze:help "Continuous monitoring commands (Ctrl-C to stop).";

        container system {
            config false;
            description "A stream is a live feed and it starts empty. It reports what happens from
                         now on. It never reports what happened before the command was typed.";
            ze:help "System-level event streams.";

            container netlink {
                config false;
                ze:command "ze-iface:monitor-system-netlink";
                ze:task-support required;
                description "Streams netlink events: route adds and deletes, link
state changes, address assignments. Filter with route, link, address, or
all.";
                ze:help "Watch kernel networking changes in real time.";
            }
        }
    }
}
