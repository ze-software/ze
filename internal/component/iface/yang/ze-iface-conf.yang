module ze-iface-conf {
    namespace "urn:ze:iface:conf";
    prefix iface;

    import ze-types { prefix zt; }
    import ze-extensions { prefix ze; }

    description "Network interface configuration for Ze";

    revision 2026-01-01 {
        description "Initial revision";
    }

    grouping interface-common {
        description "Interface properties common to all kinds (L2 and L3)";

        leaf description {
            type string {
                length "0..255";
            }
            description "Ze keeps the text in the config only, and it makes no kernel call for it. The
                         kernel link alias IFLA_IFALIAS carries ze's own ownership marker instead, so
                         a description never reaches it.";
            ze:help "Interface description";
        }

        leaf mtu {
            type uint16 {
                range "68..16000";
            }
            description "The range is 68 to 16000 bytes. Ze applies the value with the netlink call
                         LinkSetMTU after it creates the interface. Ze restores the previous value
                         when a later step of the same apply fails. When the leaf is omitted, ze makes
                         no MTU call and the device keeps its current MTU. For a device ze creates
                         that is the kernel's default for the kind: 1500 for a dummy, veth or bridge,
                         1420 for wireguard, and the underlay MTU less the encapsulation for a tunnel.
                         Each kind has its own value, so the schema declares no single default.";
            ze:help "Maximum transmission unit";
        }

        leaf os-name {
            type string;
            ze:validate "os-device-name";
            description "When this leaf is omitted, ze uses the logical name as the OS device name, so
                         every interface whose name already matches its kernel device resolves
                         unchanged. Set the leaf to alias a readable interface name to a different
                         kernel device. The iface resolver then maps the logical name to this OS device.
                         ze init records the discovered OS name here.";
            ze:help "OS device this logical interface name binds to.";
        }

        leaf disable {
            type empty;
            description "Ze skips a disabled interface at every apply step, so it creates no device,
                         it installs no address, it starts no DHCP client and it sends no router
                         advertisement. A DHCP client that is already running stops, and it takes
                         away the address and the default route its lease installed. A device ze
                         created before is deleted, because a disabled interface leaves the managed
                         set. The config block stays in place.";
            ze:help "Administratively disable this interface";
        }
    }

    grouping interface-l2 {
        description "Interface properties for kinds that expose a MAC
                     address at the list level: ethernet, dummy, veth,
                     bridge. Tunnel L2 kinds (gretap, ip6gretap) carry
                     the mac/address leaf inside their per-case containers
                     instead. L3-only kinds with no MAC (e.g. wireguard,
                     L3 tunnels) use interface-common directly.";

        uses interface-common;

        container mac {
            description "address overrides the operational MAC address. match selects the kernel device
                         by its MAC. The two leaves are independent, so ze can match a NIC by its
                         permanent factory MAC and override its operational MAC at the same time.";
            ze:help "Hardware MAC settings for this interface.";
            leaf address {
                type string {
                    pattern '[0-9a-fA-F]{2}(:[0-9a-fA-F]{2}){5}';
                }
                ze:validate "mac-address";
                description "An example value is 02:42:ac:11:00:02. Ze applies the value when it creates
                             the interface. When the leaf is omitted, the kernel assigns a MAC by
                             itself.";
                ze:help "Override the kernel-assigned MAC with a colon-separated hex value.";
            }
            leaf match {
                type string {
                    pattern '[0-9a-fA-F]{2}(:[0-9a-fA-F]{2}){5}';
                }
                ze:validate "mac-address";
                description "The binding is by MAC rather than by name. The resolver matches the
                             device's permanent factory address (IFLA_PERM_ADDRESS) when the device
                             reports one, so the binding survives an operational MAC override. For a
                             virtual device that reports no permanent address, the resolver matches the
                             current address. This leaf takes precedence over os-name. It applies to the
                             ethernet kind only, which is the matched physical kind. Ze identifies the
                             kinds it creates (dummy, veth, bridge and the rest) by the name ze assigns.
                             When the matching device is absent, the binding waits until the device
                             appears.";
                ze:help "Bind this logical interface to the kernel device that carries this hardware MAC.";
            }
        }

        container offload {
            description "Ze applies these features through a kernel ioctl, the ethtool SIOCETHTOOL
                         interface, or a sysfs write, after it creates the interface. The ethtool(8) CLI
                         program is not required, because ze talks to the kernel directly. For a boolean
                         leaf, true enables the feature explicitly, false disables it explicitly, and an
                         absent leaf preserves the OS default with no kernel call. Offload availability
                         depends on the NIC driver and the kernel version. Ze logs an unsupported
                         feature as a warning, and the config commit still succeeds.";
            ze:help "Network offload and packet steering features.";

            leaf gro {
                type boolean;
                description "GRO aggregates small incoming packets into larger ones before it passes
                             them up the network stack, which reduces the CPU cost per packet. GRO is
                             software-based, so it works on all NIC types, including veth and dummy. Ze
                             applies it through the kernel ioctl ETHTOOL_SGRO. It is equivalent to
                             'ethtool -K <dev> gro on|off'.";
                ze:help "Generic Receive Offload: aggregate small incoming packets before the network stack.";
            }

            leaf gso {
                type boolean;
                description "GSO delays the segmentation of a large outgoing packet until just before
                             the NIC driver transmit path, which reduces CPU work in the upper stack. It
                             is the software-based counterpart of TSO. Ze applies it through the kernel
                             ioctl ETHTOOL_SGSO. It is equivalent to 'ethtool -K <dev> gso on|off'.";
                ze:help "Generic Segmentation Offload: delay segmentation until the NIC driver transmit path.";
            }

            leaf sg {
                type boolean;
                description "Scatter-Gather I/O lets the NIC assemble a single frame from multiple non-
                             contiguous memory buffers, which avoids data copies. Most drivers need it
                             for TSO and GSO. Ze applies it through the kernel ioctl ETHTOOL_SSG. It is
                             equivalent to 'ethtool -K <dev> sg on|off'.";
                ze:help "Scatter-Gather I/O: build one frame from several memory buffers.";
            }

            leaf tso {
                type boolean;
                description "TSO moves TCP segmentation to the NIC hardware, so the kernel hands off a
                             TCP segment of up to 64 KB and the NIC splits it into MTU-sized frames on
                             the wire. The feature needs NIC hardware support. Disable it when the
                             interface passes traffic to VPP, or to a virtual switch that cannot handle
                             an oversized frame. Ze applies it through the kernel ioctl ETHTOOL_STSO. It
                             is equivalent to 'ethtool -K <dev> tso on|off'.";
                ze:help "TCP Segmentation Offload: the NIC splits large TCP segments into wire frames.";
            }

            leaf lro {
                type boolean;
                description "LRO is the hardware-based counterpart of GRO. It can break forwarding and
                             bridging, because the coalesced frame no longer matches the original wire
                             format. Disable it on a router or a bridge that forwards traffic between
                             interfaces. Ze applies it through the kernel ioctl ETHTOOL_SLRO. It is
                             equivalent to 'ethtool -K <dev> lro on|off'.";
                ze:help "Large Receive Offload: the NIC coalesces incoming TCP segments before DMA.";
            }

            leaf hw-tc-offload {
                type boolean;
                description "The feature lets the NIC run TC flower and u32 filter rules in hardware, so
                             a matched flow does not reach kernel processing. It needs NIC firmware
                             support, which is common on mlx5, bnxt and nfp. Ze applies it through the
                             kernel ioctl ETHTOOL_SFEATURES. It is equivalent to 'ethtool -K <dev> hw-
                             tc-offload on|off'.";
                ze:help "Hardware Traffic Control Offload: run TC filter rules in the NIC.";
            }

            leaf rps {
                type boolean;
                description "RPS hashes the packet header and steers the packet to a target CPU receive
                             queue. It helps when the NIC has fewer hardware RSS queues than the machine
                             has CPUs. When the leaf is true, ze writes a bitmask covering all online
                             CPUs to each rx queue sysfs entry, at
                             /sys/class/net/<dev>/queues/rx-*/rps_cpus. When the leaf is false, ze
                             writes 0 to each entry. RPS is not an ethtool feature, so ze uses sysfs
                             directly.";
                ze:help "Receive Packet Steering: spread incoming packets across CPUs in software.";
            }

            leaf rfs {
                type boolean;
                description "RFS extends RPS. It steers an incoming packet to the CPU where the
                             application that consumes the flow runs, which improves cache locality and
                             reduces cross-CPU cache bounces. When the leaf is true, ze sets
                             /proc/sys/net/core/rps_sock_flow_entries to 32768, and it distributes per-
                             queue rps_flow_cnt evenly across the rx queues. Enable RPS as well, because
                             RFS is only effective with RPS. RFS is not an ethtool feature, so ze uses
                             sysfs directly.";
                ze:help "Receive Flow Steering: steer a flow to the CPU that runs its application.";
            }
        }
    }

    grouping ipv6-host {
        description "The IPv6 host settings a unit and a pppoe-client share: SLAAC, Router
                     Advertisement acceptance, forwarding and the DHCPv6 client. Ze turns
                     autoconf, accept-ra and forwarding into net.ipv6.conf.<iface> sysctl
                     writes, which it emits on the event bus for the sysctl plugin to perform.";

        leaf autoconf {
            ze:backend "netlink";
            type boolean;
            description "The kernel learns an address only when a Router Advertisement reaches
                         the device it owns, so this leaf needs the netlink backend. On the vpp
                         backend, the NIC belongs to VPP, and no advertisement reaches the Linux
                         Control Plane tap.";
            ze:help "Enable IPv6 stateless autoconfiguration.";
        }

        leaf accept-ra {
            ze:backend "netlink";
            type uint8 {
                range "0..2";
            }
            default 0;
            description "This leaf needs the netlink backend, for the same reason as autoconf:
                         the two leaves describe one behavior. Above 0 it also makes the
                         device's RDNSS options (RFC 8106) an ra record of the router's
                         received DNS servers, on a unit and on a pppoe-client session alike.";
            ze:help "Accept RA level: 0 disables, 1 accepts when not forwarding, 2 accepts even when forwarding.";
        }

        leaf forwarding {
            type boolean;
            description "The leaf sets net.ipv6.conf.<iface>.forwarding. Forwarding disables RA
                         acceptance, unless accept-ra is set to 2.";
            ze:help "Allow this interface to forward IPv6 packets between interfaces.";
        }

        container dhcpv6 {
            ze:backend "netlink";
            description "The client requests addresses, delegated prefixes, or both, from a
                         DHCPv6 server. It runs alongside SLAAC when autoconf is also enabled.";
            ze:help "DHCPv6 stateful client (RFC 8415).";

            leaf enabled {
                type boolean;
                default false;
                description "Ze starts a DHCPv6 client on this interface when the leaf is true. The
                             client sends a Solicit that carries the Rapid Commit option, and
                             it takes a Reply directly when the server answers with one.
                             Otherwise it sends a Request after the Advertise.";
                ze:help "Enable DHCPv6 client";
            }

            container pd {
                description "Request a delegated prefix. Every Solicit, Request, Renew and
                             Rebind Ze sends carries an IA_PD option, and Ze publishes each
                             delegated prefix as a lease on this interface.";
                ze:help "Prefix delegation";

                leaf length {
                    type uint8 {
                        range "48..64";
                    }
                    description "The prefix length ze asks for, from 48 to 64, sent as an IA
                                 Prefix hint (::/length) in the IA_PD. Without it the IA_PD
                                 carries no hint and the server chooses the length.";
                    ze:help "Requested prefix length";
                }
            }

            leaf duid {
                type string {
                    pattern '[0-9a-fA-F]{2}(:[0-9a-fA-F]{2}){2,129}';
                }
                description "When the leaf is omitted, ze generates a DUID-LL from the interface
                             MAC. Set the leaf when the DHCP server binds a lease to a specific
                             DUID. Write it as colon-separated hex octets, such as
                             00:03:00:01:02:00:00:00:00:01: the 2-octet type code, then 1 to
                             128 octets of identifier (RFC 9915 Section 11.1).";
                ze:help "Override the DHCPv6 Unique Identifier (RFC 9915 Section 11).";
            }
        }
    }

    grouping qos-maps {
        description "Inline 802.1p QoS maps for VLAN sub-interfaces.
                     Maps translate between the 3-bit PCP field of the
                     802.1Q tag header and kernel-internal priority.";

        list ingress-qos-map {
            key "pcp";
            description "The map needs vlan-id. A frame whose PCP value has no entry keeps
priority 0.";
            ze:help "Map the 802.1p PCP value of a received tagged frame to an internal priority.";

            leaf pcp {
                type uint8 {
                    range "0..7";
                }
                description "IEEE 802.1Q defines the Priority Code Point field, which is
3 bits wide and holds a value from 0 to 7.";
                ze:help "PCP value in the 802.1Q header of the received frame.";
            }

            leaf priority {
                type uint8 {
                    range "0..7";
                }
                mandatory true;
                description "The value runs from 0 to 7.";
                ze:help "Internal priority Ze gives to a matching frame.";
            }
        }

        list egress-qos-map {
            key "priority";
            description "Ze stamps the PCP value in the 802.1Q header. The map needs vlan-id.
Ze sends a priority with no entry as PCP 0.";
            ze:help "Map the internal priority of an outgoing packet to the 802.1p PCP value.";

            leaf priority {
                type uint8 {
                    range "0..7";
                }
                description "The value runs from 0 to 7.";
                ze:help "Internal priority of the outgoing packet.";
            }

            leaf pcp {
                type uint8 {
                    range "0..7";
                }
                mandatory true;
                description "IEEE 802.1Q defines the Priority Code Point field, which is
3 bits wide and holds a value from 0 to 7.";
                ze:help "PCP value Ze stamps in the 802.1Q header.";
            }
        }
    }

    // Keep the original inline-map surface on these four interface kinds.
    // Other users of interface-unit do not acquire VLAN QoS configuration.
    augment "/iface:interface/iface:ethernet/iface:unit" {
        uses qos-maps;
    }
    augment "/iface:interface/iface:dummy/iface:unit" {
        uses qos-maps;
    }
    augment "/iface:interface/iface:veth/iface:unit" {
        uses qos-maps;
    }
    augment "/iface:interface/iface:bridge/iface:unit" {
        uses qos-maps;
    }

    grouping interface-unit {
        description "Logical interface unit properties";

        list unit {
            key "name";
            description "A unit holds the addresses, the VLAN tag and the sysctl settings of one
                         logical subinterface. A unit with a vlan-id creates a kernel subinterface
                         named <parent>.<vlan-id>. A unit without one puts its addresses on the parent
                         device.";
            ze:help "Logical interface unit";

            leaf name {
                type zt:node-name;
                description "The name is the list key and it identifies the unit in the config. It
                             does not reach the kernel. The OS device name comes from the parent
                             device and the vlan-id.";
                ze:help "Unit name (lowercase alphanumeric and hyphens)";
            }

            leaf vlan-id {
                type zt:vlan-id;
                description "The range is 1 to 4094, which is what IEEE 802.1Q allows. Ze creates a
                             kernel 802.1Q subinterface named <parent>.<vlan-id>. An L3 tunnel refuses
                             a unit that carries this leaf, because only gretap and ip6gretap carry
                             Ethernet frames.";
                ze:help "VLAN identifier";
            }

            leaf description {
                type string {
                    length "0..255";
                }
                description "Ze keeps the text in the config only, and it makes no kernel call for it.
                             The limit is 255 characters.";
                ze:help "Unit description";
            }

            leaf disable {
                type empty;
                description "Ze skips a disabled unit at apply, so it installs none of its addresses,
                             it installs no mirror, it starts no DHCP client and it sends no router
                             advertisement for the unit. A DHCP client that is already running
                             stops, and it takes away the address and the default route its lease
                             installed. A VLAN subinterface ze created for the unit is deleted. The
                             config block stays in place.";
                ze:help "Administratively disable this unit";
            }

            leaf route-priority {
                type uint32 {
                    range "0..4294966271";
                }
                default 254;
                description "A lower value is preferred. On link-down, ze increases the metric by 1024,
                             which deprioritizes the interface. The default 254 ranks a learned default
                             below a static default and below a protocol-learned one, the way rib
                             distance ranks connected 0, static 10 and ebgp 20. Write 0 to put a learned
                             default on the kernel metric that an operator's static default also uses.
                             The two then share one kernel route, and the last writer owns it. A value
                             above 0 also makes ze own the IPv6 default routes of the interface: ze sets
                             accept_ra_defrtr=0 and installs the ::/0 routes itself.";
                ze:help "Route metric for default routes learned on this unit through DHCP or router advertisement.";
            }

            leaf vrf {
                type string;
                ze:validate "unimplemented-vrf";
                description "Ze creates no VRF device and enslaves no interface, so a unit cannot use a
                             routing table other than the main table. The leaf stays in the schema so
                             that the refusal can say why. It becomes functional when VRF support ships.";
                ze:help "Not implemented. Ze refuses a config that sets this leaf.";
            }

            leaf-list sysctl-profile {
                type zt:node-name;
                max-elements 10;
                ze:syntax "bracket";
                description "The built-in profiles are dsr, router, hardened, multihomed and proxy. A
                             user-defined profile comes from a sysctl { profile ... } config block. Ze
                             applies the profiles in order, and the last one wins on a key that two
                             profiles both set.";
                ze:help "Named sysctl profiles to apply to this unit.";
            }

            container ipv4 {
                description "The container holds one unit's IPv4 state. Ze installs the addresses
                             through netlink. Ze turns each other leaf into a net.ipv4.conf.<iface>
                             sysctl write, which it emits on the event bus for the sysctl plugin to
                             perform.";
                ze:help "IPv4 addressing, forwarding, ARP behavior, and DHCP client for this unit.";

                leaf-list address {
                    type string {
                        pattern '[0-9]{1,3}\.[0-9]{1,3}\.[0-9]{1,3}\.[0-9]{1,3}/[0-9]{1,2}';
                    }
                    ze:syntax "bracket";
                    description "Ze installs each address on the unit's OS device through netlink. An
                                 address that leaves the list is removed on the next apply, because ze
                                 reconciles the whole set rather than adding to it. A unit with a
                                 vlan-id puts its addresses on <parent>.<vlan-id>.";
                    ze:help "IPv4 addresses in CIDR notation (e.g., 10.0.0.1/24)";
                }

                leaf unnumbered {
                    type zt:node-name;
                    description "The value names another interface in this config, the donor, usually
                                 loopback or a dummy. Ze installs the donor's IPv4 address on this
                                 unit as a /32, so the unit has no subnet of its own (Cisco ip
                                 unnumbered, Junos unnumbered-address). Ze refuses the leaf together
                                 with address or dhcp, and it refuses a donor that is missing, that is
                                 itself unnumbered, or that holds no IPv4 address. OSPF runs on such a
                                 unit only as a point-to-point interface.";
                    ze:help "Borrow the IPv4 address of another interface (unnumbered point-to-point)";
                }

                leaf unnumbered-source {
                    type zt:ipv4-address;
                    description "Ze installs this address of the donor as the unit's /32. The donor
                                 must hold it. When the leaf is omitted, ze takes the donor's first
                                 IPv4 address, in unit name order and then in address order (Junos
                                 preferred-source-address).";
                    ze:help "Which donor IPv4 address an unnumbered unit borrows";
                }

                leaf forwarding {
                    type boolean;
                    description "The leaf sets net.ipv4.conf.<iface>.forwarding. Routing needs it. When
                                 it is disabled, the kernel drops a packet that is not destined for a
                                 local address.";
                    ze:help "Allow this interface to forward IPv4 packets between interfaces.";
                }

                leaf arp-filter {
                    type boolean;
                    description "The leaf sets net.ipv4.conf.<iface>.arp_filter. It stops the interface
                                 from answering for an address that is assigned to another interface.
                                 Use it on a multi-homed host.";
                    ze:help "Only answer ARP requests for addresses on the receiving interface.";
                }

                leaf arp-accept {
                    type boolean;
                    description "The leaf sets net.ipv4.conf.<iface>.arp_accept. It helps a failover,
                                 where a peer announces a new MAC for an existing IP address.";
                    ze:help "Accept gratuitous ARP frames and add their entries to the ARP cache.";
                }

                leaf proxy-arp {
                    type boolean;
                    description "The leaf sets net.ipv4.conf.<iface>.proxy_arp. Use it to bridge subnets
                                 that have no L2 connectivity between them, or for an unnumbered
                                 interface. Ze refuses it on a unit that carries an IPv4 VRRP
                                 group, because the reply would carry the device MAC rather than
                                 the virtual router MAC (RFC 9568 Section 8.1.3).";
                    ze:help "Answer ARP requests for other hosts that are reachable through this router.";
                }

                leaf arp-announce {
                    type uint8 {
                        range "0..2";
                    }
                    default 0;
                    description "Ze writes the value to net.ipv4.conf.<iface>.arp_announce. Level 0
                                 puts any local address in the ARP request. Level 1 prefers an address
                                 on the target's subnet. Level 2 uses the best local address only,
                                 which the dsr sysctl profile also sets.";
                    ze:help "ARP announce level: 0=any, 1=prefer subnet, 2=best only";
                }

                leaf arp-ignore {
                    type uint8 {
                        range "0..2";
                    }
                    default 0;
                    description "0 replies to any request. 1 replies only when the target address is on
                                 the incoming interface. 2 adds a sender subnet check to level 1.";
                    ze:help "ARP ignore level, which selects the ARP requests this interface answers.";
                }

                leaf rpf-check {
                    type enumeration {
                        enum disable { ze:help "No source address check, rp_filter 0."; }
                        enum strict { ze:help "Drop a packet whose source does not route back through this interface, rp_filter 1."; }
                        enum loose { ze:help "Drop a packet whose source address has no route at all, rp_filter 2."; }
                    }
                    description "Ze writes the value to net.ipv4.conf.<iface>.rp_filter, where disable
                                 is 0, strict is 1 and loose is 2. strict drops a packet whose source
                                 address would not route back through this interface. loose drops a
                                 packet whose source address has no route at all. With backend vpp, Ze
                                 also enables VPP uRPF in the same mode on the interface's receive path.";
                    ze:help "Reverse path filtering mode";
                }

                container dhcp {
                    ze:backend "netlink";
                    description "Ze runs its own DHCPv4 client, so no dhclient process and no udhcpc
                                 process is needed. The client installs the leased address, the
                                 default route and the resolvers that the server sends.";
                    ze:help "DHCPv4 client configuration";

                    leaf enabled {
                        type boolean;
                        default false;
                        description "Ze starts one client when this leaf is true, and it stops the
                                     client when the leaf goes false. The client is keyed by the
                                     interface name and the unit name, so two units on one interface
                                     run two clients.";
                        ze:help "Enable DHCPv4 client";
                    }

                    leaf client-id {
                        type string;
                        description "When the leaf is omitted, ze uses the MAC address. Set it for an
                                     environment where the DHCP server keys a lease on the client-id
                                     rather than on the MAC.";
                        ze:help "DHCP option 61 client identifier, sent in DISCOVER and REQUEST messages.";
                    }

                    leaf hostname {
                        type string;
                        description "Ze sends the value as DHCP option 12 in the DISCOVER message and
                                     in the REQUEST message. When the leaf is omitted, ze sends no
                                     option 12 at all.";
                        ze:help "Hostname in DHCP requests";
                    }
                }
            }

            container ipv6 {
                description "The container holds one unit's IPv6 state. Ze installs the addresses
                             through netlink. Ze turns autoconf, accept-ra and forwarding into
                             net.ipv6.conf.<iface> sysctl writes, which it emits on the event bus for
                             the sysctl plugin to perform.";
                ze:help "IPv6 addressing, forwarding, autoconfiguration, and DHCPv6 client for this unit.";

                leaf-list address {
                    type string {
                        pattern '[0-9a-fA-F:]{2,39}/[0-9]{1,3}';
                    }
                    ze:syntax "bracket";
                    description "Ze installs each address on the unit's OS device through netlink. An
                                 address that leaves the list is removed on the next apply, because ze
                                 reconciles the whole set rather than adding to it.";
                    ze:help "IPv6 addresses in CIDR notation (e.g., fd00::1/64)";
                }

                uses ipv6-host;

                list delegated-prefix {
                    ze:backend "netlink";
                    key "source";
                    description "Ze takes one /64 for this unit out of the prefix the named pppoe-client
                                 leases through DHCPv6 prefix delegation (RFC 7084 L-2): the delegated
                                 prefix plus subnet-id, shifted into the bits between the delegated
                                 length and 64. The unit's address is that /64 plus
                                 interface-identifier, and its preferred and valid lifetimes never
                                 exceed what remains of the delegation (RFC 9915 Section 6.3). With
                                 router-advertisement enabled, the unit advertises the /64 in a Prefix
                                 Information option and the delegated prefix in a Route Information
                                 option. Ze refuses a source that is not a pppoe-client requesting a
                                 delegated prefix, a subnet-id the pd length cannot hold, and two units
                                 taking the same subnet-id from one source.";
                    ze:help "Number this unit from a prefix delegated to a pppoe-client.";

                    leaf source {
                        type string;
                        ze:reference "pppoe-client-delegation";
                        description "The name of a pppoe-client whose ipv6 dhcpv6 pd container is set.
                                     The editor completes the pppoe-clients that request a delegated
                                     prefix; commit refuses any other name at interface verify.";
                        ze:help "The pppoe-client that leases the delegated prefix.";
                    }

                    leaf subnet-id {
                        type uint16;
                        mandatory true;
                        description "Which /64 of the delegated prefix this unit takes. With pd length 56
                                     the ids run from 0 to 255; with no pd length, the largest id is
                                     65535, the /48 maximum. An id the delegation the server chose
                                     cannot hold leaves the unit without a /64, and Ze logs it.";
                        ze:help "The /64 within the delegated prefix (0 to 2^(64 - pd length) - 1).";
                    }

                    leaf interface-identifier {
                        type zt:ipv6-address;
                        default "::1";
                        description "Only the low 64 bits are used; Ze refuses a value with any of the
                                     high 64 bits set.";
                        ze:help "The host part of the unit's address in the /64 (default ::1).";
                    }
                }

                leaf rpf-check {
                    type enumeration {
                        enum disable { ze:help "No source address validation."; }
                        enum strict { ze:help "Drop a packet whose source address does not route back through this interface."; }
                        enum loose { ze:help "Drop a packet whose source address has no route at all."; }
                    }
                    description "strict drops a packet whose source address would not be routed back
                                 through this interface. loose drops a packet whose source address has
                                 no route at all. disable performs no source address validation.";
                    ze:backend "netlink";
                    ze:help "Reverse path filtering mode, enforced by an nftables fib lookup.";
                }

                container router-advertisement {
                    ze:os "linux";
                    ze:backend "netlink";
                    description "Ze advertises prefixes, flags and resolvers on this link, so that a
                                 host autoconfigures. That is the role radvd fills on another system.
                                 Sending is separate from accepting: set forwarding true on an
                                 advertising interface, and leave accept-ra at 0 unless this interface
                                 also learns from another router.";
                    ze:help "Router Advertisement sender (RFC 4861).";

                    leaf enabled {
                        type boolean;
                        default false;
                        description "RFC 4861 Section 6.2.1 requires AdvSendAdvertisements to default to
                                     false, so a node never becomes a router by accident.";
                        ze:help "Send Router Advertisements on this unit.";
                    }

                    leaf maximum-interval {
                        type uint16 {
                            range "4..1800";
                        }
                        units seconds;
                        default 600;
                        description "RFC 4861 Section 6.2.1 defines MaxRtrAdvInterval. Ze picks each
                                     interval at random between minimum-interval and this value.";
                        ze:help "Longest time between unsolicited Router Advertisements (MaxRtrAdvInterval).";
                    }

                    leaf minimum-interval {
                        type uint16 {
                            range "3..1350";
                        }
                        units seconds;
                        default 200;
                        description "RFC 4861 Section 6.2.1 defines MinRtrAdvInterval. The value must
                                     not exceed 0.75 x maximum-interval, and config verify rejects a
                                     larger value.";
                        ze:help "Shortest time between unsolicited Router Advertisements (MinRtrAdvInterval).";
                    }

                    leaf router-lifetime {
                        type uint16 {
                            range "0..9000";
                        }
                        units seconds;
                        default 1800;
                        description "RFC 4861 Section 6.2.1 defines AdvDefaultLifetime. 0 says that Ze
                                     is not a default router, and the prefixes and the resolvers in the
                                     advertisement still apply. Any other value must be at least
                                     maximum-interval, and config verify rejects a smaller one.";
                        ze:help "How long a host keeps Ze in its default router list (AdvDefaultLifetime).";
                    }

                    leaf hop-limit {
                        type uint8;
                        default 64;
                        description "RFC 4861 Section 4.2 defines AdvCurHopLimit. 0 means that this
                                     router states no value.";
                        ze:help "Value a host places in the Hop Limit field of its outgoing packets.";
                    }

                    leaf managed {
                        type boolean;
                        default false;
                        description "Ze sets bit 0x80 of the flags octet in the Router Advertisement.
                                     Set the flag only where a DHCPv6 server answers on this link,
                                     because the flag alone gives a host no address.";
                        ze:help "Set the M flag: hosts get their addresses from DHCPv6
                                 (RFC 4861 Section 4.2).";
                    }

                    leaf other-config {
                        type boolean;
                        default false;
                        description "Ze sets bit 0x40 of the flags octet in the Router Advertisement.
                                     The flag does not change how a host builds its addresses. Use the
                                     rdnss container instead where no DHCPv6 server runs on this
                                     link.";
                        ze:help "Set the O flag: hosts get other configuration, such as DNS,
                                 from DHCPv6 (RFC 4861 Section 4.2).";
                    }

                    leaf reachable-time {
                        type uint32 {
                            range "0..3600000";
                        }
                        units milliseconds;
                        default 0;
                        description "RFC 4861 Section 6.2.1 defines AdvReachableTime. 0 means that this
                                     router states no value.";
                        ze:help "How long a host treats a neighbor as reachable after a reachability confirmation.";
                    }

                    leaf retransmit-timer {
                        type uint32;
                        units milliseconds;
                        default 0;
                        description "RFC 4861 Section 6.2.1 defines AdvRetransTimer. 0 means that this
                                     router states no value.";
                        ze:help "Time between retransmitted Neighbor Solicitations on this link.";
                    }

                    list prefix {
                        key "prefix";
                        description "Ze sends the host bits below the prefix length as zero.";
                        ze:help "Prefixes advertised in Prefix Information options (RFC 4861 Section 4.6.2).";

                        leaf prefix {
                            type zt:prefix-ipv6;
                            description "Stateless autoconfiguration needs a 64-bit prefix (RFC 4862
                                         Section 5.5.3).";
                            ze:help "Advertised IPv6 prefix in CIDR notation, for example 2001:db8:1::/64.";
                        }

                        leaf on-link {
                            type boolean;
                            default true;
                            description "Ze sets bit 0x80 of the flags octet in the Prefix Information
                                         option. With the flag clear, a host sends a packet for an
                                         address in this prefix to the router rather than straight to
                                         the neighbor.";
                            ze:help "Set the L flag: hosts treat addresses in this prefix as
                                     on-link (RFC 4861 Section 4.6.2).";
                        }

                        leaf autonomous {
                            type boolean;
                            default true;
                            description "With the A flag set, a host builds addresses from this prefix
                                         by stateless autoconfiguration (RFC 4862).";
                            ze:help "Set the A flag in the Prefix Information option.";
                        }

                        leaf valid-lifetime {
                            type uint32;
                            units seconds;
                            default 2592000;
                            description "4294967295 means that the prefix never expires. The default is
                                         30 days.";
                            ze:help "How long the prefix stays valid (RFC 4861 Section 4.6.2).";
                        }

                        leaf preferred-lifetime {
                            type uint32;
                            units seconds;
                            default 604800;
                            description "RFC 4861 Section 4.6.2 defines the preferred lifetime. The
                                         value must not exceed valid-lifetime, and config verify rejects
                                         a larger value. The default is 7 days.";
                            ze:help "How long an address built from the prefix stays preferred.";
                        }
                    }

                    container rdnss {
                        description "The option points a link at a resolver without a DHCPv6 server.";
                        ze:help "Recursive DNS servers advertised to hosts (RFC 8106 Section 5.1).";

                        leaf-list server {
                            type zt:ipv6-address;
                            ze:syntax "bracket";
                            max-elements 8;
                            description "Ze puts every address in ONE RDNSS option, which is why they
                                         share one lifetime. The option carries 8 addresses at most,
                                         and it grows by 16 bytes for each address.";
                            ze:help "Resolver addresses. All of them share lifetime.";
                        }

                        leaf lifetime {
                            type uint32;
                            units seconds;
                            description "0 tells a host to stop using the resolvers, and an operator can
                                         set it. 4294967295 means that the resolvers never expire. This
                                         leaf has no default: leave it out, and Ze sends 3 x maximum-
                                         interval, the value RFC 8106 Section 5.1 recommends. 0 is not
                                         the default for that reason, because Ze could not then tell an
                                         operator who retires a resolver from one who set nothing.";
                            ze:help "How long a host can use these resolvers (RFC 8106 Section 5.1).";
                        }

                        uses zt:dns-source {
                            refine dns-source {
                                description "The sources of this unit's RDNSS option, in order. configured is
                                    server; received is every IPv6 resolver Ze learned by DHCPv6, a Router
                                    Advertisement or the host's own resolv.conf; self is this unit's own global
                                    or unique-local address, none when it holds no such address. radius is
                                    refused here. A loopback or a link-local address with no zone is never
                                    advertised, whatever its source, and each one dropped is logged. The option
                                    carries 8 addresses at most. With the container absent the default is source
                                    configured, then received, mode first-usable: the server entries when any
                                    are set, otherwise the learned resolvers. A learned resolver is advertised
                                    with a lifetime no longer than what remains of its lease, and a resolver the
                                    unit stops advertising is sent once with lifetime 0. Write source configured
                                    alone to keep a unit with no server from sending RDNSS.";
                            }
                        }
                    }
                }
            }

            container mirror {
                ze:os "linux";
                ze:backend "netlink vpp";
                description "The netlink backend mirrors through tc mirred. The vpp backend programs
                             SPAN, through sw_interface_span_enable_disable, and it maps the ingress
                             direction and the egress direction onto the RX SPAN state and the TX SPAN
                             state, as a device-level port mirror.";
                ze:help "Traffic mirroring for this interface.";

                leaf ingress {
                    type string;
                    description "Ze installs a tc mirred filter that copies each received frame toward
                                 the named interface. Ze resolves the name through the same selector
                                 map as the source, so a capture port bound by mac/match or aliased by
                                 os-name works. An unbound name installs no mirror.";
                    ze:help "Mirror ingress traffic to this interface";
                }

                leaf egress {
                    type string;
                    description "Ze installs a tc mirred filter that copies each transmitted frame
                                 toward the named interface. Ze resolves the name through the same
                                 selector map as the source, so a capture port bound by mac/match or
                                 aliased by os-name works. An unbound name installs no mirror.";
                    ze:help "Mirror egress traffic to this interface";
                }
            }

            container mpls {
                ze:os "linux";
                description "Ze turns the enable leaf below into a net.mpls.conf.<iface>.input sysctl
                             write. The size of the global label table is a separate sysctl,
                             net.mpls.platform_labels, which the sysctl config block sets.";
                ze:help "MPLS forwarding on this interface (RFC 3031 LSR).";

                leaf enable {
                    type boolean;
                    default false;
                    description "The leaf sets net.mpls.conf.<iface>.input. net.mpls.platform_labels
                                 sets the size of the global label table.";
                    ze:help "Enable MPLS label input on this interface.";
                }
            }
        }
    }

    grouping tunnel-v4-endpoints {
        description "IPv4 underlay endpoints for a tunnel.";

        container local {
            description "Set exactly one of ip and interface. Ze refuses both together with 'local ip
                         and local interface are mutually exclusive', and it refuses neither with
                         'local ip or local interface required'.";
            ze:help "Local IPv4 endpoint or source interface (one of ip or interface)";

            leaf ip {
                type zt:ipv4-address;
                description "Ze writes the address into the netlink Local field, so it becomes the
                             source address of the outer IPv4 header. Use interface instead where the
                             underlay address is learned by DHCP and can change.";
                ze:help "Local IPv4 endpoint";
            }

            leaf interface {
                type string;
                description "Ze looks the device up and passes its kernel index as the netlink parent
                             field, so the kernel takes the source address from that device. The vxlan
                             case refuses this leaf and needs a local ip.";
                ze:help "Local interface to take the source address from";
            }
        }

        container remote {
            description "The remote endpoint is mandatory, so ze builds no unnumbered tunnel and no
                         multipoint tunnel. One tunnel interface reaches one remote endpoint.";
            ze:help "Remote IPv4 endpoint";

            leaf ip {
                type zt:ipv4-address;
                mandatory true;
                description "Ze writes the address into the netlink Remote field, so it becomes the
                             destination address of the outer IPv4 header. For a vxlan tunnel this
                             address is the remote VTEP.";
                ze:help "Remote IPv4 endpoint";
            }
        }
    }

    grouping tunnel-v6-endpoints {
        description "IPv6 underlay endpoints for a tunnel.";

        container local {
            description "Set exactly one of ip and interface. Ze refuses both together with 'local ip
                         and local interface are mutually exclusive', and it refuses neither with
                         'local ip or local interface required'.";
            ze:help "Local IPv6 endpoint or source interface (one of ip or interface)";

            leaf ip {
                type zt:ipv6-address;
                description "Ze writes the address into the netlink Local field, so it becomes the
                             source address of the outer IPv6 header. Use interface instead where the
                             underlay address is learned by a Router Advertisement and can change.";
                ze:help "Local IPv6 endpoint";
            }

            leaf interface {
                type string;
                description "Ze looks the device up and passes its kernel index as the netlink parent
                             field, so the kernel takes the source address from that device.";
                ze:help "Local interface to take the source address from";
            }
        }

        container remote {
            description "The remote endpoint is mandatory, so ze builds no unnumbered tunnel and no
                         multipoint tunnel. One tunnel interface reaches one remote endpoint.";
            ze:help "Remote IPv6 endpoint";

            leaf ip {
                type zt:ipv6-address;
                mandatory true;
                description "Ze writes the address into the netlink Remote field, so it becomes the
                             destination address of the outer IPv6 header.";
                ze:help "Remote IPv6 endpoint";
            }
        }
    }

    container interface {
        description "An interface name must not be one of the CLI reserved keywords: brief, scan, type,
                     errors, counters. Each of these collides with the 'show interface' and 'clear
                     interface' command grammar. 'show interface counters' would be ambiguous if an
                     interface were named counters. iface.ValidateIfaceName rejects a reserved name at
                     apply time, with a clear error. The kernel does not enforce this on its own.";
        ze:help "Network interface configuration.";

        leaf backend {
            type string;
            default "netlink";
            description "Ze loads the backend this name selects, and it refuses an unknown name with
                         'unknown backend' and the list of registered names. netlink drives the Linux
                         kernel through rtnetlink. vpp drives the VPP data plane, and it is linked in
                         only under the ze_vpp build tag.";
            ze:help "Interface management backend: netlink or vpp.";
        }

        leaf dhcp-auto {
            type boolean;
            default false;
            description "Use this leaf when the interface name is not known at config time, for example
                         on a gokrazy appliance. Ze ignores the leaf when any explicit DHCP config
                         exists.";
            ze:help "Auto-discover the first ethernet interface and run DHCP on it.";
        }

        list ethernet {
            key "name";
            unique "mac/address";
            unique "mac/match";
            description "Ze manages the interface's addresses, MTU, offload settings and units. The
                         interface must already exist in the OS, because ze does not create a physical
                         interface.";
            ze:help "Physical or virtual Ethernet interface.";

            leaf name {
                type string;
                description "Ze creates no physical interface, so the name must match a device the OS
                             already carries. Where the logical name and the kernel device differ, set
                             os-name to alias the device, or set mac/match to bind by hardware
                             address.";
                ze:help "OS interface name (e.g., eth0, ens3). Must match an existing kernel interface.";
            }

            uses interface-l2;
            uses interface-unit;
        }

        list dummy {
            key "name";
            description "Ze creates the interface when it does not exist. Use it to host a service
                         address that is not tied to a physical link, for example a router-id or an
                         anycast VIP.";
            ze:help "Dummy interface, which behaves like a loopback.";

            leaf name {
                type string;
                description "Ze creates the device with the netlink call LinkAdd and sets it up. The
                             length is 1 to 15 characters, and a slash, a space and the sequence '..'
                             are refused.";
                ze:help "Interface name (e.g., dummy0). Ze creates the interface at apply time.";
            }

            uses interface-l2;
            uses interface-unit;
        }

        list veth {
            key "name";
            unique "mac/address";
            ze:backend "netlink";
            description "A veth is a pair of connected devices, and a packet that enters one end
                         leaves the other. Ze creates both ends in one netlink call and sets both up.
                         The pair exists only while ze manages it, so ze deletes it when the entry
                         leaves the config.";
            ze:help "Virtual ethernet pair interface";

            leaf name {
                type string;
                description "This name is the end ze manages: it carries the addresses, the units and
                             the MTU. Ze creates the pair with one netlink LinkAdd call, then it sets
                             the link state of both ends to up.";
                ze:help "Veth interface name (e.g., veth0). Ze creates the pair at apply time.";
            }

            leaf peer {
                type string;
                description "Ze validates the peer name with the same rules as name. Ze sets the peer
                             link state to up right after it creates the pair. The schema gives the
                             peer end no units, so ze puts no address on it.";
                ze:help "Veth peer name";
            }

            uses interface-l2;
            uses interface-unit;
        }

        list bridge {
            key "name";
            unique "mac/address";
            ze:backend "netlink";
            description "Ze creates the bridge when it does not exist. Ze enslaves the member interfaces
                         at apply time.";
            ze:help "Linux bridge interface, which forwards Ethernet frames between member ports at L2.";

            leaf name {
                type string;
                description "Ze creates the bridge with the netlink call LinkAdd when the device is
                             absent. The member leaf-list then enslaves each port to this device.";
                ze:help "Bridge interface name (e.g., br0). Ze creates the bridge at apply time.";
            }

            leaf stp {
                ze:os "linux";
                type boolean;
                default false;
                description "Ze writes 1 or 0 to /sys/class/net/<bridge>/bridge/stp_state. The default
                             false leaves the bridge with no loop protection, so it forwards a frame
                             as soon as a port comes up. Set it true where two ports can reach the
                             same L2 segment.";
                ze:help "Enable Spanning Tree Protocol";
            }

            leaf-list member {
                ze:os "linux";
                type string;
                ze:syntax "bracket";
                description "Ze enslaves each named port with the netlink call LinkSetMaster. A port
                             that leaves the list is released with LinkSetNoMaster on the next apply.
                             Each name must be an interface the config or the OS already carries.";
                ze:help "Member port interface names";
            }

            uses interface-l2;
            uses interface-unit;
        }

        list tunnel {
            key "name";
            ze:backend "netlink";
            description "The choice below selects the encapsulation kind, and each case carries only the
                         leaves that are valid for that kind. The local endpoint and remote endpoint
                         pattern matches bgp peer connection { local { ip ... } remote { ip ... } }.";
            ze:help "Tunnel interface, in the GRE, GRETAP, IPIP, SIT or IP6TNL family.";

            leaf name {
                type string;
                description "Ze creates the kernel netdev under this name. The length is 1 to 15
                             characters. A slash, a space and the sequence '..' are refused, because
                             the name reaches a /proc/sys/net/ipv4/conf/<name>/ path.";
                ze:help "Interface name (free-form, validated by iface naming rules)";
            }

            container encapsulation {
                description "The container holds exactly one case of the kind choice below, and that
                             choice is mandatory. A tunnel with no case is refused with 'encapsulation
                             block has no kind selected'. A tunnel with no encapsulation container is
                             refused with 'missing encapsulation block'.";
                ze:help "Tunnel encapsulation kind and per-kind parameters";

                choice kind {
                    mandatory true;
                    description "The schema cannot represent an invalid combination, for example a key
                                 on ipip.";
                    ze:help "Encapsulation kind of this tunnel.";

                    case gre {
                        description "The case selects the Linux gre kind, which puts a GRE header
                                     between the outer IPv4 header and the inner packet. RFC 2890 adds
                                     the optional Key field, and the key leaf below sets it.";
                        ze:help "GRE over IPv4 (RFC 2784, key extension RFC 2890). L3.";
                        container gre {
                            ze:backend "netlink vpp";
                            description "Ze builds a netlink Gretun link over IPv4 endpoints. The kind
                                         is L3, so a unit that carries a vlan-id on this tunnel is
                                         refused. Use the gretap kind where the tunnel must carry
                                         Ethernet frames.";
                            ze:help "GRE-over-IPv4 parameters";
                            uses tunnel-v4-endpoints;

                            leaf key {
                                type uint32;
                                description "Ze writes the value into the netlink IKey field and the
                                             netlink OKey field, so one key covers the input direction
                                             and the output direction. The value 0 cannot be set,
                                             because the netlink library reads 0 as no key and leaves
                                             the GRE Key flag clear.";
                                ze:help "32-bit GRE key (RFC 2890). Symmetric: same
                                         value used for input and output";
                            }

                            leaf ttl {
                                // netlink only: GreTunnelV2 and IpipTunnel
                                // (vendor/go.fd.io/govpp/binapi) carry no hop-limit value, and only
                                // tunnel_types.Tunnel does, which the gre and ipip APIs do not take.
                                // Inherit alone would be reachable through the encap flag
                                // TUNNEL_API_ENCAP_DECAP_FLAG_ENCAP_COPY_HOP_LIMIT, which ze does
                                // not set. So netlink implements this leaf and vpp does not.
                                ze:backend "netlink";
                                type uint8;
                                default 64;
                                description "Ze writes the value into the outer IPv4 TTL field,
                                             through the netlink field Ttl. The default 64 gives the
                                             encapsulated packet its own budget of underlay hops, and
                                             it matches the hoplimit default of the IPv6-underlay
                                             kinds. 0 makes the kernel take the value from the inner
                                             packet instead, which drops the packet early when the
                                             inner TTL is small or the underlay is more than one hop.
                                             Only the netlink backend implements the leaf. The vpp
                                             tunnel API carries no outer TTL, so a commit that names
                                             a ttl on the vpp backend is refused by path.";
                                ze:help "Outer-header TTL. 0 = inherit from the inner packet";
                            }

                            leaf tos {
                                type uint8;
                                default 0;
                                description "Ze writes the value into the outer IPv4 Type of Service
                                             field, through the netlink field Tos. 0 makes the kernel
                                             copy the inner packet's own value, which carries a DSCP
                                             marking across the tunnel.";
                                ze:help "Outer-header Type of Service. 0 = inherit";
                            }

                            leaf no-pmtu-discovery {
                                type empty;
                                description "Ze sets the netlink field PMtuDisc to 0 when this leaf is
                                             present, and to 1 when it is absent. Path MTU Discovery
                                             is therefore on by default. Set the leaf where the
                                             underlay path drops the ICMP Fragmentation Needed message
                                             that discovery needs.";
                                ze:help "Disable Path MTU Discovery on the outer header";
                            }
                        }
                    }

                    case gretap {
                        description "The case selects the Linux gretap kind, which carries whole
                                     Ethernet frames over GRE. It is one of the two kinds ze counts as
                                     bridgeable. A unit on it can therefore carry a vlan-id, and the
                                     case carries its own mac container.";
                        ze:help "GRE over IPv4, L2 (Ethernet over GRE, bridgeable). RFC 2784.";
                        container gretap {
                            ze:backend "netlink vpp";
                            description "Ze builds a netlink Gretap link over IPv4 endpoints. The
                                         kernel selects the GRE protocol type 0x6558, Transparent
                                         Ethernet Bridging, from the link kind alone, so no leaf sets
                                         it.";
                            ze:help "GRETAP-over-IPv4 parameters";
                            uses tunnel-v4-endpoints;

                            leaf key {
                                type uint32;
                                description "Ze writes the value into the netlink IKey field and the
                                             netlink OKey field, so one key covers the input direction
                                             and the output direction. The value 0 cannot be set,
                                             because the netlink library reads 0 as no key and leaves
                                             the GRE Key flag clear.";
                                ze:help "32-bit GRE key (RFC 2890)";
                            }

                            leaf ttl {
                                // netlink only: GreTunnelV2 and IpipTunnel
                                // (vendor/go.fd.io/govpp/binapi) carry no hop-limit value, and only
                                // tunnel_types.Tunnel does, which the gre and ipip APIs do not take.
                                // Inherit alone would be reachable through the encap flag
                                // TUNNEL_API_ENCAP_DECAP_FLAG_ENCAP_COPY_HOP_LIMIT, which ze does
                                // not set. So netlink implements this leaf and vpp does not.
                                ze:backend "netlink";
                                type uint8;
                                default 64;
                                description "Ze writes the value into the outer IPv4 TTL field,
                                             through the netlink field Ttl. The default 64 gives the
                                             encapsulated packet its own budget of underlay hops, and
                                             it matches the hoplimit default of the IPv6-underlay
                                             kinds. 0 makes the kernel take the value from the inner
                                             packet instead, which drops the packet early when the
                                             inner TTL is small or the underlay is more than one hop.
                                             Only the netlink backend implements the leaf. The vpp
                                             tunnel API carries no outer TTL, so a commit that names
                                             a ttl on the vpp backend is refused by path.";
                                ze:help "Outer-header TTL. 0 = inherit from the inner packet";
                            }

                            leaf tos {
                                type uint8;
                                default 0;
                                description "Ze writes the value into the outer IPv4 Type of Service
                                             field, through the netlink field Tos. 0 makes the kernel
                                             copy the inner packet's own value, which carries a DSCP
                                             marking across the tunnel.";
                                ze:help "Outer-header Type of Service. 0 = inherit";
                            }

                            leaf no-pmtu-discovery {
                                type empty;
                                description "Ze sets the netlink field PMtuDisc to 0 when this leaf is
                                             present, and to 1 when it is absent. Path MTU Discovery
                                             is therefore on by default. Set the leaf where the
                                             underlay path drops the ICMP Fragmentation Needed message
                                             that discovery needs.";
                                ze:help "Disable Path MTU Discovery on the outer header";
                            }

                            container mac {
                                description "An L2 tunnel kind carries its MAC leaf here rather than
                                             in the shared interface-l2 grouping, because an L3 kind
                                             has no MAC at all. Ze reads the container for the gretap
                                             kind and the ip6gretap kind only.";
                                ze:help "Hardware MAC settings (L2 tunnel kinds only)";
                                leaf address {
                                    type string {
                                        pattern '[0-9a-fA-F]{2}(:[0-9a-fA-F]{2}){5}';
                                    }
                                    ze:validate "mac-address";
                                    description "Ze applies the value after it creates the netdev,
                                                 with the netlink call LinkSetHardwareAddr. When the
                                                 leaf is omitted, ze makes no MAC call, and the device
                                                 keeps the address the kernel gave it.";
                                    ze:help "Hardware MAC address (L2 tunnel kinds only)";
                                }
                            }
                        }
                    }

                    case ip6gre {
                        description "The case selects the Linux ip6gre kind, which puts the GRE header
                                     in an outer IPv6 header. Ze builds it from the same netlink
                                     Gretun type as gre, and the endpoint family selects the kernel
                                     kind.";
                        ze:help "GRE over IPv6 (RFC 2784, key extension RFC 2890). L3.";
                        container ip6gre {
                            description "The endpoints are IPv6, so this container carries hoplimit
                                         and tclass where an IPv4 kind carries ttl and tos. The kind
                                         is L3, so a unit that carries a vlan-id on this tunnel is
                                         refused.";
                            ze:help "GRE-over-IPv6 parameters";
                            uses tunnel-v6-endpoints;

                            leaf key {
                                type uint32;
                                description "Ze writes the value into the netlink IKey field and the
                                             netlink OKey field, so one key covers the input direction
                                             and the output direction. The value 0 cannot be set,
                                             because the netlink library reads 0 as no key and leaves
                                             the GRE Key flag clear.";
                                ze:help "32-bit GRE key (RFC 2890)";
                            }

                            leaf hoplimit {
                                type uint8;
                                default 64;
                                description "Ze writes the value into the outer IPv6 Hop Limit field,
                                             through the netlink field Ttl. The field limits how many
                                             underlay routers the encapsulated packet can cross before
                                             one of them drops it.";
                                ze:help "Outer IPv6 hop limit (RFC 2473 Section 6.3)";
                            }

                            leaf tclass {
                                type uint8;
                                default 0;
                                description "Ze writes the value into the outer IPv6 Traffic Class
                                             field, through the netlink field Tos. The field carries
                                             the DSCP marking of the encapsulated packet across the
                                             underlay.";
                                ze:help "Outer IPv6 traffic class (RFC 2473 Section 6.4)";
                            }
                        }
                    }

                    case ip6gretap {
                        description "The case selects the Linux ip6gretap kind, which carries whole
                                     Ethernet frames over GRE in an outer IPv6 header. It is the
                                     second of the two kinds ze counts as bridgeable.";
                        ze:help "GRE over IPv6, L2 (Ethernet over GRE bridgeable). RFC 2784.";
                        container ip6gretap {
                            description "Ze builds a netlink Gretap link over IPv6 endpoints. The
                                         endpoints are IPv6, so the container carries hoplimit and
                                         tclass where the gretap case carries ttl and tos.";
                            ze:help "GRETAP-over-IPv6 parameters";
                            uses tunnel-v6-endpoints;

                            leaf key {
                                type uint32;
                                description "Ze writes the value into the netlink IKey field and the
                                             netlink OKey field, so one key covers the input direction
                                             and the output direction. The value 0 cannot be set,
                                             because the netlink library reads 0 as no key and leaves
                                             the GRE Key flag clear.";
                                ze:help "32-bit GRE key (RFC 2890)";
                            }

                            leaf hoplimit {
                                type uint8;
                                default 64;
                                description "Ze writes the value into the outer IPv6 Hop Limit field,
                                             through the netlink field Ttl. The field limits how many
                                             underlay routers the encapsulated packet can cross before
                                             one of them drops it.";
                                ze:help "Outer IPv6 hop limit";
                            }

                            leaf tclass {
                                type uint8;
                                default 0;
                                description "Ze writes the value into the outer IPv6 Traffic Class
                                             field, through the netlink field Tos. The field carries
                                             the DSCP marking of the encapsulated packet across the
                                             underlay.";
                                ze:help "Outer IPv6 traffic class";
                            }

                            container mac {
                                description "An L2 tunnel kind carries its MAC leaf here rather than
                                             in the shared interface-l2 grouping, because an L3 kind
                                             has no MAC at all. Ze reads the container for the gretap
                                             kind and the ip6gretap kind only.";
                                ze:help "Hardware MAC settings (L2 tunnel kinds only)";
                                leaf address {
                                    type string {
                                        pattern '[0-9a-fA-F]{2}(:[0-9a-fA-F]{2}){5}';
                                    }
                                    ze:validate "mac-address";
                                    description "Ze applies the value after it creates the netdev,
                                                 with the netlink call LinkSetHardwareAddr. When the
                                                 leaf is omitted, ze makes no MAC call, and the device
                                                 keeps the address the kernel gave it.";
                                    ze:help "Hardware MAC address (L2 tunnel kinds only)";
                                }
                            }
                        }
                    }

                    case ipip {
                        description "The case selects the Linux ipip kind, which puts an IPv4 packet
                                     directly in an outer IPv4 header with Protocol 4. There is no GRE
                                     header, so no key can separate two tunnels between the same
                                     endpoint pair.";
                        ze:help "IPv4 in IPv4 (RFC 2003). No GRE header, no key. L3.";
                        container ipip {
                            ze:backend "netlink vpp";
                            description "Ze builds a netlink Iptun link and sets Proto to
                                         IPPROTO_IPIP. The kind is L3, so a unit that carries a
                                         vlan-id on this tunnel is refused at parse time.";
                            ze:help "IPv4-in-IPv4 tunnel parameters (RFC 2003). Minimal overhead, no key support.";
                            uses tunnel-v4-endpoints;

                            leaf ttl {
                                // netlink only: GreTunnelV2 and IpipTunnel
                                // (vendor/go.fd.io/govpp/binapi) carry no hop-limit value, and only
                                // tunnel_types.Tunnel does, which the gre and ipip APIs do not take.
                                // Inherit alone would be reachable through the encap flag
                                // TUNNEL_API_ENCAP_DECAP_FLAG_ENCAP_COPY_HOP_LIMIT, which ze does
                                // not set. So netlink implements this leaf and vpp does not.
                                ze:backend "netlink";
                                type uint8;
                                default 64;
                                description "Ze writes the value into the outer IPv4 TTL field,
                                             through the netlink field Ttl. The default 64 gives the
                                             encapsulated packet its own budget of underlay hops, and
                                             it matches the hoplimit default of the IPv6-underlay
                                             kinds. 0 makes the kernel take the value from the inner
                                             packet instead, which drops the packet early when the
                                             inner TTL is small or the underlay is more than one hop.
                                             Only the netlink backend implements the leaf. The vpp
                                             tunnel API carries no outer TTL, so a commit that names
                                             a ttl on the vpp backend is refused by path.";
                                ze:help "Outer-header TTL. 0 = inherit from the inner packet";
                            }

                            leaf tos {
                                type uint8;
                                default 0;
                                description "Ze writes the value into the outer IPv4 Type of Service
                                             field, through the netlink field Tos. 0 makes the kernel
                                             copy the inner packet's own value, which carries a DSCP
                                             marking across the tunnel.";
                                ze:help "Outer-header Type of Service. 0 = inherit";
                            }

                            leaf no-pmtu-discovery {
                                type empty;
                                description "Ze sets the netlink field PMtuDisc to 0 when this leaf is
                                             present, and to 1 when it is absent. Path MTU Discovery
                                             is therefore on by default. Set the leaf where the
                                             underlay path drops the ICMP Fragmentation Needed message
                                             that discovery needs.";
                                ze:help "Disable Path MTU Discovery on the outer header";
                            }
                        }
                    }

                    case sit {
                        description "The case selects the Linux sit kind, which carries IPv6 in an
                                     outer IPv4 header with Protocol 41. Ze sets the netlink field
                                     Proto to IPPROTO_IPV6. Use the kind to reach an IPv6 network over
                                     an IPv4-only underlay.";
                        ze:help "IPv6 in IPv4 (6in4, RFC 4213 Section 3). L3.";
                        container sit {
                            description "Ze builds a netlink Sittun link. The endpoints are IPv4 and
                                         the payload is IPv6, so the container carries no key leaf.
                                         The kind is L3, so a unit that carries a vlan-id on this
                                         tunnel is refused.";
                            ze:help "SIT (6in4) parameters";
                            uses tunnel-v4-endpoints;

                            leaf ttl {
                                type uint8;
                                default 64;
                                description "Ze writes the value into the outer IPv4 TTL field,
                                             through the netlink field Ttl. The default 64 gives the
                                             encapsulated packet its own budget of underlay hops, and
                                             it matches the hoplimit default of the IPv6-underlay
                                             kinds. 0 makes the kernel take the value from the inner
                                             packet instead, which drops the packet early when the
                                             inner TTL is small or the underlay is more than one hop.";
                                ze:help "Outer-header TTL. 0 = inherit from the inner packet";
                            }

                            leaf tos {
                                type uint8;
                                default 0;
                                description "Ze writes the value into the outer IPv4 Type of Service
                                             field, through the netlink field Tos. 0 makes the kernel
                                             copy the inner packet's own value, which carries a DSCP
                                             marking across the tunnel.";
                                ze:help "Outer-header Type of Service. 0 = inherit";
                            }

                            leaf no-pmtu-discovery {
                                type empty;
                                description "Ze sets the netlink field PMtuDisc to 0 when this leaf is
                                             present, and to 1 when it is absent. Path MTU Discovery
                                             is therefore on by default. Set the leaf where the
                                             underlay path drops the ICMP Fragmentation Needed message
                                             that discovery needs.";
                                ze:help "Disable Path MTU Discovery on the outer header";
                            }
                        }
                    }

                    case ip6tnl {
                        description "The case selects the Linux ip6tnl kind, and ze sets the netlink
                                     field Proto to IPPROTO_IPV6, which is 41. The same kernel kind
                                     serves the ipip6 case, and the inner protocol number is the only
                                     thing that separates the two.";
                        ze:help "IPv6 in IPv6 (RFC 2473). Also covers ip6ip6. L3.";
                        container ip6tnl {
                            description "Ze builds a netlink Ip6tnl link over IPv6 endpoints. A
                                         read-back of an existing device reports the kind as ip6tnl
                                         for this case and for ipip6, because the kernel drops the
                                         inner protocol number. Ze therefore cannot separate the two
                                         from kernel state alone.";
                            ze:help "IPv6-in-IPv6 tunnel parameters (RFC 2473). Also handles ip6ip6 encapsulation.";
                            uses tunnel-v6-endpoints;

                            leaf hoplimit {
                                type uint8;
                                default 64;
                                description "Ze writes the value into the outer IPv6 Hop Limit field,
                                             through the netlink field Ttl. The field limits how many
                                             underlay routers the encapsulated packet can cross before
                                             one of them drops it.";
                                ze:help "Outer IPv6 hop limit (RFC 2473 Section 6.3)";
                            }

                            leaf tclass {
                                type uint8;
                                default 0;
                                description "Ze writes the value into the outer IPv6 Traffic Class
                                             field, through the netlink field Tos. The field carries
                                             the DSCP marking of the encapsulated packet across the
                                             underlay.";
                                ze:help "Outer IPv6 traffic class (RFC 2473 Section 6.4)";
                            }

                            leaf encaplimit {
                                type uint8;
                                default 4;
                                description "RFC 2473 Section 4.1.1 defines the value as how many
                                             further levels of encapsulation are permitted for the
                                             packet. Ze writes it into the netlink field EncapLimit,
                                             and the kernel sends it as an IPv6 destination option.";
                                ze:help "Tunnel encapsulation limit (RFC 2473 Section 4.1.1)";
                            }
                        }
                    }

                    case ipip6 {
                        description "Ze implements this case through the ip6tnl Linux kind, with
                                     Proto=IPPROTO_IPIP.";
                        ze:help "IPv4 in IPv6 (RFC 2473 with Next Header = 4). L3.";
                        container ipip6 {
                            description "Ze builds the same netlink Ip6tnl link as the ip6tnl case,
                                         and it sets Proto to IPPROTO_IPIP, which is 4. The endpoints
                                         are IPv6 and the payload is IPv4. The kernel reports the
                                         device kind as ip6tnl either way.";
                            ze:help "IPv4-in-IPv6 tunnel parameters (RFC 2473, Next Header = 4). Uses the ip6tnl kernel kind.";
                            uses tunnel-v6-endpoints;

                            leaf hoplimit {
                                type uint8;
                                default 64;
                                description "Ze writes the value into the outer IPv6 Hop Limit field,
                                             through the netlink field Ttl. The field limits how many
                                             underlay routers the encapsulated packet can cross before
                                             one of them drops it.";
                                ze:help "Outer IPv6 hop limit";
                            }

                            leaf tclass {
                                type uint8;
                                default 0;
                                description "Ze writes the value into the outer IPv6 Traffic Class
                                             field, through the netlink field Tos. The field carries
                                             the DSCP marking of the encapsulated packet across the
                                             underlay.";
                                ze:help "Outer IPv6 traffic class";
                            }

                            leaf encaplimit {
                                type uint8;
                                default 4;
                                description "RFC 2473 Section 4.1.1 defines the value as how many
                                             further levels of encapsulation are permitted for the
                                             packet. Ze writes it into the netlink field EncapLimit,
                                             and the kernel sends it as an IPv6 destination option.";
                                ze:help "Tunnel encapsulation limit";
                            }
                        }
                    }

                    case vxlan {
                        description "The case is implemented in the netlink backend and in the VPP
                                     backend.";
                        ze:help "VXLAN overlay: L2 Ethernet frames over a UDP/IPv4 underlay, keyed by a 24-bit VNI.";
                        container vxlan {
                            ze:backend "netlink vpp";
                            description "Ze builds a netlink Vxlan link, and it refuses a local
                                         interface source, so the local endpoint must be an ip. The
                                         VPP backend implements the same kind through
                                         VxlanAddDelTunnelV3. A unit that carries a vlan-id on this
                                         tunnel is refused, because ze counts only gretap and
                                         ip6gretap as bridgeable.";
                            ze:help "VXLAN parameters. local ip is the tunnel
                                     source, remote ip the (unicast) VTEP
                                     destination.";
                            uses tunnel-v4-endpoints;

                            leaf vni {
                                type uint32 {
                                    range "1..16777215";
                                }
                                mandatory true;
                                description "The VNI separates overlays that share one underlay, so
                                             two VXLAN tunnels between the same endpoints need
                                             different values. Ze refuses 0 and any value more
                                             than 16777215, in the netlink backend and in the VPP
                                             backend.";
                                ze:help "VXLAN Network Identifier (24-bit, 1..16777215)";
                            }

                            leaf port {
                                type zt:port;
                                default 4789;
                                description "4789 is the port IANA assigns to VXLAN. Ze sends the
                                             value as the netlink destination port, and 0 selects
                                             4789. Change it only where an underlay device or a
                                             firewall expects another port.";
                                ze:help "UDP destination port (IANA-assigned default 4789)";
                            }
                        }
                    }
                }
            }

            uses interface-common;
            uses interface-unit;
        }

        list wireguard {
            key "name";
            ze:listener;
            ze:backend "netlink vpp";
            description "The interface level carries listen-port, fwmark and private-key, and a nested
                         peer list. Each peer carries public-key, endpoint, allowed-ips, preshared-key
                         and persistent-keepalive. WireGuard is an L3 kind with no MAC address, so it
                         uses interface-common rather than interface-l2. Ze reconciles each peer in
                         place, through the wgctrl ConfigureDevice call. Adding a peer, removing one, or
                         rekeying one does not disturb the netdev or any other peer.";
            ze:help "WireGuard interface, configured declaratively.";

            leaf name {
                type string;
                description "Ze creates the kernel netdev under this name. The length is 1 to 15
                             characters. A slash, a space and the sequence '..' are refused, because
                             the name reaches a /proc/sys/net/ipv4/conf/<name>/ path.";
                ze:help "Interface name (free-form, validated by iface naming rules)";
            }

            leaf listen-port {
                type zt:port;
                description "When the leaf is unset, the kernel chooses an ephemeral port on the first
                             outbound handshake.";
                ze:help "UDP port WireGuard binds on 0.0.0.0 and :: for handshake and data traffic.";
            }

            leaf fwmark {
                type uint32;
                default 0;
                description "Ze passes the value to the kernel through the wgctrl call
                             ConfigureDevice. The kernel then sets the mark on each encapsulated UDP
                             packet, and a policy routing rule or an nftables rule can match it. Ze
                             always sends the leaf, so a config that clears the mark clears the kernel
                             state too.";
                ze:help "Firewall mark applied to outgoing encapsulated
                         packets for policy routing. 0 means unset.";
            }

            leaf private-key {
                mandatory true;
                type string;
                ze:sensitive;
                description "Ze stores the key $9$-encoded on disk, through the standard ze sensitive-
                             leaf pattern, and it decodes the key to plaintext base64 at parse time. 'ze
                             config show' and 'ze config dump' always emit the $9$ form, never the
                             plaintext. The $9$ form is obfuscation and not encryption, so protect the
                             config file at the filesystem level with chmod 600, the same way as a BGP
                             MD5 password.";
                ze:help "Base64-encoded 32-byte Curve25519 private key.";
            }

            list peer {
                key "name";
                description "Each peer has its own set of allowed-ips, which define the traffic that is
                             routed through the tunnel.";
                ze:help "WireGuard peer, identified by its public key.";

                leaf name {
                    type string;
                    description "The kernel matches a peer by its public key, and this name never
                                 reaches the kernel. Ze uses the name as the list key, and in the
                                 error message of a peer that fails to apply. A rename therefore
                                 produces the same kernel peer set.";
                    ze:help "Config-level peer name (free-form label, used as list key). Not sent on the wire.";
                }

                leaf public-key {
                    type string;
                    mandatory true;
                    description "The kernel matches an inbound handshake to a peer by this key. The
                                 key is public, so it carries no ze:sensitive marker, and ze stores it
                                 in plaintext where private-key and preshared-key are $9$-encoded.";
                    ze:help "Base64-encoded 32-byte Curve25519 peer public key";
                }

                leaf preshared-key {
                    type string;
                    ze:sensitive;
                    description "The key is mixed into the handshake for post-quantum resistance. Ze
                                 stores it $9$-encoded on disk, the same pattern as private-key.";
                    ze:help "Optional base64-encoded 32-byte symmetric preshared key.";
                }

                container endpoint {
                    description "Both leaves are required together. The kernel uses this address on the
                                 first outbound handshake, and it updates the address on every inbound
                                 handshake from a new source address.";
                    ze:help "Remote UDP endpoint for this peer.";

                    leaf ip {
                        type zt:ip-address;
                        description "Ze parses the value with net.ParseIP, so a hostname is refused at
                                     apply time. When the endpoint is absent, ze sends no address to
                                     the kernel, and the peer must start the handshake.";
                        ze:help "Remote IPv4 or IPv6 address (numeric, not
                                 a hostname -- DNS resolution is not performed)";
                    }

                    leaf port {
                        type zt:port;
                        description "The value is the listen-port the peer sets on its own side. Ze
                                     combines the port with ip into one UDP address for the kernel, so
                                     a port with no ip reaches nothing.";
                        ze:help "Remote UDP port";
                    }
                }

                leaf-list allowed-ips {
                    type string {
                        pattern '[0-9a-fA-F:][0-9a-fA-F:.]*(/[0-9]{1,3})?';
                    }
                    ze:syntax "bracket";
                    description "An inbound packet from this peer must have a source address inside one
                                 of these prefixes. That check is cryptokey routing.";
                    ze:help "CIDR prefixes routed into the tunnel for this peer.";
                }

                leaf persistent-keepalive {
                    type uint16 {
                        range "0..65535";
                    }
                    default 0;
                    description "0 disables the keepalives. A usual value is 25.";
                    ze:help "Seconds between unsolicited keepalive packets that maintain NAT state.";
                }

                leaf disable {
                    type empty;
                    description "Ze removes the peer from the kernel peer set on reload, and the peer
                                 stays in the config.";
                    ze:help "Administratively disable this peer.";
                }
            }

            uses interface-common;
            uses interface-unit;
        }

        list xfrm {
            key "name";
            ze:os "linux";
            ze:backend "netlink";
            description "The kernel XFRM subsystem encrypts and decrypts the traffic that is routed into
                         this interface. The if-id binds security associations to the interface. XFRM is
                         an L3 kind with no MAC address.";
            ze:help "XFRM interface, for route-based IPsec (Linux 4.19 and later).";

            leaf name {
                type string;
                description "Ze creates the XFRM netdev under this name. The length is 1 to 15
                             characters. A slash, a space and the sequence '..' are refused, because
                             the name reaches a /proc/sys/net/ipv4/conf/<name>/ path.";
                ze:help "Interface name (free-form, validated by iface naming rules)";
            }

            leaf if-id {
                mandatory true;
                type uint32 {
                    range "1..4294967295";
                }
                description "A bound security association carries the same if_id. The value must be non-
                             zero, because 0 means unset in the kernel.";
                ze:help "XFRM identifier that binds security associations to this interface.";
            }

            leaf dev {
                type string;
                description "When the leaf is set, ze binds the XFRM interface to this physical device.
                             When the leaf is omitted, the interface is unbound, and it uses the routing
                             table to select the underlay.";
                ze:help "Optional parent device that this XFRM interface binds to.";
            }

            uses interface-common;
            uses interface-unit;
        }

        list pppoe-client {
            key "name";
            ze:os "linux";
            ze:backend "netlink";
            description "The client dials an access concentrator over a physical Ethernet interface,
                         negotiates LCP, authentication, IPCP and, when ipv6 is enabled, IPv6CP, and
                         presents the PPP session as a routable interface with server-assigned
                         addresses. Ze creates the kernel
                         device under the configured name through rtnetlink (kind ppp with
                         IFLA_PPP_DEV_FD), so the name an operator writes is the name static routes,
                         firewall matches and NAT see on every session and every reconnect.";
            ze:help "PPPoE client interface (RFC 2516).";

            leaf name {
                type string {
                    length "1..15";
                    pattern '[A-Za-z][A-Za-z0-9_.-]*';
                }
                description "Ze creates the PPP session device under this name through rtnetlink
                             (kind ppp with IFLA_PPP_DEV_FD), so the operator names the kernel
                             device, not a logical alias. Every consumer that names an interface
                             (static routes, firewall matches, NAT) reaches the session through this
                             name, and the name follows a PPPoE unit renumber. The kernel limits an
                             interface name to 15 octets (IFNAMSIZ 16 including NUL). The name must
                             not collide with another configured interface of any kind.";
                ze:help "Configured interface name (e.g. pppoe0), carried onto the kernel device.";
            }

            leaf source-interface {
                mandatory true;
                type string;
                description "Ze opens a raw discovery socket bound to this device and sends the PADI
                             frame on it. The source MAC of the frame is the device's own hardware
                             address.";
                ze:help "Physical Ethernet interface for PPPoE discovery
                         (e.g. eth2). Must exist and be admin-up.";
            }

            container authentication {
                description "LCP negotiation decides which of PAP and CHAP ze uses. Ze answers PAP
                             with an Authenticate-Request that carries the username as the Peer-ID. Ze
                             answers CHAP with a Response that carries the MD5 digest and the
                             username.";
                ze:help "PPPoE authentication credentials (PAP or CHAP)";

                leaf username {
                    mandatory true;
                    type string {
                        length "1..255";
                    }
                    description "Ze puts the value in the Peer-ID field of a PAP Authenticate-Request,
                                 or in the Name field of a CHAP Response. The length is 1 to 255
                                 characters.";
                    ze:help "Authentication username sent to the AC";
                }

                leaf password {
                    mandatory true;
                    type string {
                        length "1..255";
                    }
                    ze:sensitive;
                    description "The $9$ form is obfuscation and not encryption, so protect the config
                                 file at the filesystem level with chmod 600. Ze sends the password in
                                 a PAP Authenticate-Request. For CHAP, ze sends no password. It
                                 computes the MD5 digest over the Identifier, the password and the
                                 Challenge Value.";
                    ze:help "Authentication password. Stored $9$-encoded
                             on disk via the standard ze sensitive-leaf
                             pattern.";
                }
            }

            leaf service-name {
                type string {
                    length "0..255";
                }
                description "Ze puts the value in the Service-Name tag of the PADI frame and of the
                             PADR frame. An empty value sends a zero-length tag, which every access
                             concentrator answers.";
                ze:help "Desired PPPoE service name. Empty or absent
                         means accept any service (RFC 2516 Section 5.1).";
            }

            leaf ac-name {
                type string {
                    length "0..255";
                }
                description "When the leaf is set, ze accepts a PADO frame only from this access
                             concentrator. An empty or absent value accepts any access concentrator.";
                ze:help "Desired access concentrator name.";
            }

            leaf no-default-route {
                type empty;
                description "When the leaf is absent, which is the default, ze installs a default route
                             after IPCP completes.";
                ze:help "Do not install a default route through the PPP interface.";
            }

            leaf route-priority {
                type uint32 {
                    range "0..4294966271";
                }
                default 254;
                description "A lower value is preferred. The default 254 ranks this learned default
                             below a static default and below a protocol-learned one, and it matches the
                             route-priority default on a unit. Write 0 to put the route on the kernel
                             metric that an operator's static default also uses. The two then share one
                             kernel route, and the last writer owns it.";
                ze:help "Route metric of the default route installed after IPCP completes.";
            }

            container keepalive {
                description "Ze sends an LCP Echo-Request on the session every interval and
                             counts the requests the access concentrator leaves unanswered. Any
                             Echo-Reply resets the count. The session ends on the unanswered
                             request that reaches the failure count, and the client then
                             reconnects. A change to these leaves keeps the running session up:
                             the next session uses the new values. Detection takes about interval
                             times failures seconds. A small interval with failures 1 can end
                             a session on a lossy line that is still usable.";
                ze:help "Dead-peer detection by LCP Echo-Request (RFC 1661 Section 5.8).";

                leaf interval {
                    type uint16 {
                        range "1..3600";
                    }
                    units seconds;
                    default 10;
                    description "Ze sends one LCP Echo-Request each interval while the session is
                                 up. The range is 1 to 3600 seconds and the default is 10.";
                    ze:help "Seconds between two LCP Echo-Requests.";
                }

                leaf failures {
                    type uint8 {
                        range "1..255";
                    }
                    default 3;
                    description "The session ends when this many Echo-Requests in a row have no
                                 Echo-Reply. The range is 1 to 255 and the default is 3, so the
                                 default detection time is about 30 seconds.";
                    ze:help "Unanswered Echo-Requests in a row that end the session.";
                }
            }

            container reconnect {
                description "After a session ends or a dial fails, ze waits before the next
                             discovery. The first wait is delay-min. Each further failure doubles
                             the wait, up to delay-max. A session that reaches the up state resets
                             the wait to delay-min. delay-max must not be below delay-min. A change
                             to these leaves keeps the running session up and applies to the next
                             wait.";
                ze:help "Hold-off between two dial attempts after a session ends.";

                leaf delay-min {
                    type uint16 {
                        range "1..3600";
                    }
                    units seconds;
                    default 1;
                    description "The wait before the first redial after a failure. The range is 1
                                 to 3600 seconds and the default is 1.";
                    ze:help "Seconds to wait before the first redial.";
                }

                leaf delay-max {
                    type uint16 {
                        range "1..3600";
                    }
                    units seconds;
                    default 60;
                    description "The doubling wait stops growing at this value. The range is 1 to
                                 3600 seconds and the default is 60. It must be equal to or above
                                 delay-min.";
                    ze:help "Longest wait between two redials.";
                }
            }

            container ipv6 {
                description "When enabled is true, the client negotiates IPv6CP (RFC 5072) beside IPCP
                             and independently of it, and installs on the session device the
                             link-local address formed from the negotiated interface identifier. An
                             access concentrator that rejects or ignores IPv6CP leaves the IPv4
                             session up. Ze writes autoconf, accept-ra and forwarding to the session
                             device each time a session creates it. Write accept-ra 2 with forwarding
                             true for a router that learns its default route from the access
                             concentrator's Router Advertisements. The DHCPv6 client runs on the
                             session device and takes its DUID-LL from the source interface, because
                             a PPP device has no hardware address.";
                ze:help "IPv6 on the PPPoE session: IPv6CP, SLAAC, RA and DHCPv6 client.";

                leaf enabled {
                    type boolean;
                    default false;
                    description "Ze refuses the other ipv6 leaves while enabled is not true, because
                                 without IPv6CP no IPv6 reaches the session device.";
                    ze:help "Negotiate IPv6CP on the session.";
                }

                uses ipv6-host;
            }

            uses interface-common;
        }

        container loopback {
            description "The interface is always present, and ze manages its addresses and units. Use it
                         to host a router-id address that is reachable from any interface.";
            ze:help "The system loopback interface (lo).";

            uses interface-unit;
        }

        container monitor {
            description "Ze reads no value under this container, so nothing below it changes the
                         behavior of the daemon.";
            ze:help "Interface monitoring settings";

            leaf loopback {
                type boolean;
                default false;
                description "Ze reads no value under the monitor container, so this leaf changes no
                             behavior whether it is true or false. The default is false.";
                ze:help "Monitor loopback interface";
            }
        }
    }
}
