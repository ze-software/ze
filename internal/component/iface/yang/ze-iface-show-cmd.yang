module ze-iface-show-cmd {
    namespace "urn:ze:iface:show:cmd";
    prefix ifaceshowcmd;
    import ze-extensions { prefix ze; }
    description "show route / show neighbor / show arp command tree. Owned by the iface component because these handlers read the kernel neighbor and routing tables through the iface backend. Commands are object-rooted (no shared 'ip' container); see ai/rules/plugin-self-containment.md and docs/architecture/cli/command-namespacing.md.";
    revision 2026-08-29 { description "Declare the value the description spelled in prose, so the model states the grammar and the generated usage line reads it."; }
    revision 2026-06-26 { description "Object-rooted the kernel-table reads: show ip route -> show route, show ip arp -> show neighbor (with show arp as an IPv4 alias); dropped the show ip container and the show neighbors / show kernel-routes aliases."; }
    revision 2026-06-03 { description "Relocated show ip / neighbors / kernel-routes out of the central show schema (plugin self-containment)."; }

    container show {
        config false;
        ze:help "Read-only commands to inspect system, protocol, and network state.";

        container route {
            config false;
            ze:command "ze-iface:show-route";
            description "Lists installed routes with next-hop, interface, protocol,
and metric. Pass a CIDR prefix or 'default' to filter, or a route limit to cap
the output.";
            ze:help "Show the kernel routing table.";
            leaf prefix {
                type string;
                description "A prefix in CIDR form, or the word default. Only routes for
that prefix are listed, and every route is listed when it is absent.";
                ze:help "CIDR prefix filter";
            }
            leaf limit {
                type uint32;
                description "The largest number of routes the answer carries, given after
the word limit. The default is 100000, and the answer says when it was truncated.";
                ze:help "Maximum number of routes";
            }

            container lookup {
                config false;
                ze:command "ze-iface:show-route-lookup";
                ze:rpc "ze-cli-show-api:route-lookup";
                description "Performs a longest-prefix-match and returns the
matching route with gateway, interface, protocol, and metric.";
                ze:help "Look up which route the kernel would use for a given IP.";
                leaf ip {
                    type string { pattern '[0-9a-fA-F:.]+(%[a-zA-Z0-9_.-]+)?'; }
                    mandatory true;
                    description "One IPv4 or IPv6 address without a prefix length. The
kernel answers with the route it selects for a packet to that address.";
                    ze:help "Destination IP address to look up";
                }
            }
        }

        container neighbor {
            config false;
            ze:command "ze-iface:show-neighbor";
            description "Lists IPv4 ARP and IPv6 ND entries with MAC addresses and
states. Pass ipv4 or ipv6 to filter by address family. No argument shows both.
For the IPv4-only view, 'show arp' is a shortcut.";
            ze:help "Show the ARP and neighbor discovery table.";
            leaf family {
                type enumeration {
                    enum ipv4 { ze:help "List the IPv4 ARP entries only."; }
                    enum ipv6 { ze:help "List the IPv6 neighbor discovery entries only."; }
                    enum any { ze:help "List both families, the same as no argument."; }
                    enum all { ze:help "List both families, a synonym of any."; }
                }
                description "Selects the address family the answer carries. The default
when it is absent is both families.";
                ze:help "Address family filter";
            }
        }

        container arp {
            config false;
            ze:command "ze-iface:show-arp";
            description "Lists IPv4 ARP entries with MAC address and state. ARP is
IPv4-only. Use 'show neighbor' for both families or 'show neighbor ipv6' for
the IPv6 ND table.";
            ze:help "Show the IPv4 ARP table (shortcut for 'show neighbor ipv4').";
        }
    }
}
