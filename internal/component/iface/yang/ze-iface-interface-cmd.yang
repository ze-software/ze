module ze-iface-interface-cmd {
    namespace "urn:ze:iface:interface:cmd";
    prefix ifaceifcmd;
    import ze-extensions { prefix ze; }
    // The show interface family holds interface, brief, scan, type, errors, rate,
    // and name detail/counters. The iface component owns the module because every
    // handler reads or resets interface state through the iface backend:
    // iface.ListInterfaces, GetInterface, DiscoverInterfaces, GetRate and
    // ClearCounters. The subtrees container-merge onto the show, monitor, and
    // clear verb roots. See ai/rules/plugin-self-containment.md.
    description "The show interface, monitor interface rate, and clear interface counters command tree.";
    // The model now states the grammar, and the generated usage line reads it.
    // The WAN side reports what its DHCPv6 lease delegated, and the LAN side the
    // /64 each unit derived from it, with the lifetimes that remain.
    revision 2026-11-08 { description "show interface pppoe-client reports delegated-prefixes; show interface delegated-prefix reports each LAN unit's derived /64 and its source."; }
    revision 2026-10-17 { description "clear interface counters alone is refused; clear interface counters all resets every interface."; }
    revision 2026-08-29 { description "Declare the value the description spelled in prose."; }
    // The show interface family, monitor interface rate, and clear interface
    // counters left the central show, monitor, and clear schemas, for plugin
    // self-containment.
    revision 2026-06-03 { description "Relocated the interface commands into the iface component."; }
    // They shared ze-iface:show-interface with the parent container, so each became an
    // ALIAS path of one wire method. The dispatcher registers the longest path
    // and consumes the keyword, and the handler that switched on it never saw it.
    // show interface errors returned every interface, show interface brief
    // returned full detail, and show interface type <t> answered with usage text.
    // The wire methods now match the sibling scan, detail and counters pattern,
    // one path each.
    revision 2026-08-03 { description "Gave brief, type, errors, and rate their own wire methods."; }

    container show {
        config false;
        ze:help "Read-only commands to inspect system, protocol, and network state.";

        container interface {
            config false;
            ze:command "ze-iface:show-interface";
            description "Without arguments, returns all interfaces with full detail.
Subcommands: brief, type <t>, errors, rate [<name>], pppoe-client,
delegated-prefix, name <name> detail, name <name> counters.";
            ze:help "Show network interfaces on this box.";

            container brief {
                config false;
                ze:command "ze-iface:show-interface-brief";
                description "It is the quick way to see what is up and what
addresses are assigned.";
                ze:help "One-line summary per interface: name, state, IP, and MTU.";
            }

            container scan {
                config false;
                ze:command "ze-iface:show-interface-scan";
                description "Returns name, Ze type (ethernet, bridge, vxlan, etc.),
and MAC for each interface found. Pipe to table, yaml, or json for different
views. Use it during initial setup to see what the box has.";
                ze:help "Discover and classify all OS interfaces.";
            }

            container pppoe-client {
                config false;
                ze:command "ze-iface:show-interface-pppoe-client";
                description "One object per configured PPPoE client: its state, source
interface, session id, local and peer address, uptime, and the DNS servers
learned from IPCP (RFC 1877), primary first. dns-servers is an empty list
when the access concentrator supplied none; a configured system name-server
still takes precedence in resolv.conf. delegated-prefixes lists each prefix
the client's DHCPv6 lease holds (RFC 9915 IA_PD) as prefix, valid-lifetime and
preferred-lifetime, sorted by prefix: the lifetimes are the whole seconds that
remain at the moment of the answer, 4294967295 meaning infinite, and the list
is empty when no prefix is delegated.";
                ze:help "Show PPPoE client sessions, the DNS servers they learned and their delegated prefixes.";
            }

            container delegated-prefix {
                config false;
                ze:command "ze-iface:show-interface-delegated-prefix";
                description "One object per delegated-prefix entry of every enabled
unit, sorted by interface, unit and source: interface, unit, source (the
pppoe-client whose lease delegates the prefix), subnet-id, and state. state is
installed when the unit holds its address, which adds device, address (the
unit's address with its /64 length), prefix (the derived /64), delegated (the
whole delegated prefix), valid-lifetime and preferred-lifetime (whole seconds
remaining, 4294967295 meaning infinite). waiting means the source holds no
delegated prefix; too-small means the delegated prefix cannot hold the
subnet-id; not-installed means the address install failed. Each of those
three carries a reason, and the last two name the delegated prefix.";
                ze:help "Show the /64 each LAN unit takes from a delegated prefix, and its source.";
            }

            container type {
                config false;
                ze:command "ze-iface:show-interface-type";
                description "Types include ethernet, bridge, vxlan, wireguard,
tunnel, bond, and more. If you pick an invalid type, the error lists all valid
ones.";
                ze:help "Show only interfaces of a given type.";
                leaf type {
                    type string { length "1..32"; }
                    mandatory true;
                    description "The type name the backend reports for an interface, compared
without regard to case. When no interface has it, the error lists the types present.";
                    ze:help "Ze interface type to filter by";
                }
            }

            container errors {
                config false;
                ze:command "ze-iface:show-interface-errors";
                description "Filters to only interfaces with non-zero Rx/Tx error or
drop counters. It is the quick way to find troubled links.";
                ze:help "Show interfaces that have errors or drops.";
            }

            container rate {
                config false;
                ze:command "ze-iface:show-interface-rate";
                description "Returns rx/tx bytes and packets per second. Pass an
interface name to narrow the output. Requires the rate tracker. For continuous
monitoring, use 'monitor interface rate' instead.";
                ze:help "Show per-second traffic rates on your interfaces.";
            }

            container name {
                config false;
                description "The keyword takes the interface name, and detail or counters
follows it. Without a name, show interface answers every interface.";
                ze:help "Select one interface by name.";

                container detail {
                    config false;
                    ze:command "ze-iface:show-interface-detail";
                    description "The answer is the whole record the backend holds for that
interface, and the counters are part of it. An unknown name is reported as the backend's own
error.";
                    ze:help "Show full detail for one interface.";
                    leaf name {
                        type string;
                        mandatory true;
                        description "The interface whose record is shown. The backend looks it
up by this name, and an unknown name answers the backend's error.";
                        ze:help "Interface name";
                    }
                }

                container counters {
                    config false;
                    ze:command "ze-iface:show-interface-counters";
                    description "The answer is the interface name and its Rx and Tx statistics.
A backend that keeps no statistics for the interface answers no counters available rather
than an error.";
                    ze:help "Show counters for one interface.";
                    leaf name {
                        type string;
                        mandatory true;
                        description "The interface whose statistics are read. The answer
repeats this name beside the Rx and Tx values.";
                        ze:help "Interface name";
                    }
                }
            }
        }
    }

    container monitor {
        config false;
        ze:help "Continuous monitoring commands (Ctrl-C to stop).";

        container interface {
            config false;
            description "Only rate sits under this keyword today, and it streams until you stop
it. show interface rate reads the same numbers once.";
            ze:help "Interface traffic monitoring.";

            container rate {
                config false;
                ze:command "ze-iface:monitor-interface-rate";
                ze:task-support required;
                description "Shows rx/tx bytes and packets per second, updating
every second. Optionally pass an interface name to watch just one link.";
                ze:help "Stream per-second traffic rates for your interfaces.";
            }
        }
    }

    container clear {
        config false;

        container interface {
            config false;
            description "clear interface counters all resets every managed interface, and
clear interface name <name> counters resets one. The bare clear interface counters is
refused: it names no target, and Ze never resets everything unless all is typed.";
            ze:help "Reset interface traffic counters.";

            container counters {
                config false;
                description "Clear interface counters alone is refused: say all to reset every
interface, or use clear interface name <name> counters for one. Everything is never the
default.";
                ze:help "Zero interface Rx/Tx counters: all, or clear interface name <name> counters.";

                container all {
                    config false;
                    ze:command "ze-iface:clear-interface-counters";
                    ze:rpc "ze-cli-clear-api:interface-counters";
                    description "One call resets every interface the backend manages, and the answer
reports the scope as all. Nothing else about the interfaces changes.";
                    ze:help "Zero the Rx/Tx counters for every managed interface.";
                }
            }

            container name {
                config false;
                description "The keyword takes the interface name, and counters follows it. The
answer reports that name as the scope it cleared.";
                ze:help "Select one interface by name.";

                container counters {
                    config false;
                    ze:command "ze-iface:clear-interface-counters";
                    ze:rpc "ze-cli-clear-api:interface-counters";
                    description "Only the named interface is reset. Ze translates the name to
its kernel device first, so a name bound to hardware by a selector clears the right port.";
                    ze:help "Zero the Rx/Tx counters for one interface.";
                    leaf name {
                        type string;
                        mandatory true;
                        description "The interface whose counters are reset. The answer names
it as the scope cleared, where clear interface counters all reports all.";
                        ze:help "Interface name";
                    }
                }
            }
        }
    }
}
