module ze-iface-cmd {
    namespace "urn:ze:iface:cmd";
    prefix ifacecmd;
    import ze-extensions { prefix ze; }
    import ze-types { prefix zt; }
    description "Create, configure, and manage network interfaces";
    revision 2026-08-30 { description "Declare the five values request interface migrate takes, as the keyword groups an operator types: from, to and address are required, create and timeout are not. The grammar is in the model, so completion offers each keyword and the published usage line states the form."; }
    revision 2026-08-29 { description "Declare the values the descriptions spelled in prose: the VLAN id of every unit command, the CIDR prefix of every address command, the veth peer, the MTU byte count and the MAC address. The grammar is in the model, so the renderer states it and the dispatcher types it. The interface name of request interface up, down, mtu and mac moves to the interface container, which is the keyword the operator types it after; request interface migrate names two interfaces of its own, so it states ze:inherit none."; }
    revision 2026-07-03 { description "Typed name selector on create/delete interface (create interface dummy name <n>, delete interface name <n>) per cli-grammar.md Typed Selectors."; }
    revision 2026-06-04 { description "Verb-first grammar: create/delete/request interface"; }

    typedef ip-prefix {
        type union {
            type string { pattern '([0-9]{1,3}\.){3}[0-9]{1,3}(/[0-9]{1,2})?'; }
            type string { pattern '[0-9a-fA-F:.]+(%[a-zA-Z0-9_.-]+)?(/[0-9]{1,3})?'; }
        }
        description "An IPv4 or IPv6 address, with an optional prefix length.";
    }

    typedef iface-unit {
        type string { pattern '[^ /?]+\.[0-9]+'; }
        description "An interface and one of its units, written as name.unit. Unit 0 is the interface itself.";
    }

    typedef duration {
        type string { pattern '([0-9]+(\.[0-9]+)?(ns|us|ms|s|m|h))+'; }
        description "A time span, written as a number and a unit: 30s, 2m, 1h30m.";
    }

    container create {
        config false;
        description "The interface commands create a dummy, veth or bridge interface, a VLAN unit,
and an IP address. 'create bgp peer' sits under this verb too, declared by the
BGP peer command module.";
        ze:help "Create new resources.";

        container interface {
            config false;
            description "Give the type keyword, dummy or bridge, when the interface does not
exist yet. The unit and address forms then create the interface first.";
            ze:help "Create interfaces, units, and addresses.";

            container dummy {
                config false;
                description "A second create of the same name changes nothing and reports that
the interface is present. It fails when that name holds an interface of another type.";
                ze:help "Create a dummy (loopback-style) interface.";

                container name {
                    config false;
                    ze:command "ze-iface:interface-create-dummy";
                    ze:rpc "ze-iface-api:interface-create-dummy";
                    ze:backend "netlink";
                    ze:ensure-exists "ze-iface:interface-delete";
                    description "The command is idempotent. When a unit or address command under
it fails, and this command created the interface, the interface is deleted again.";
                    ze:help "Create a dummy (loopback-style) interface.";
                    leaf name {
                        type string;
                        mandatory true;
                        description "The name of the dummy to create. A name that holds an
interface of another type is refused, and the error names both types.";
                        ze:help "Interface name";
                    }

                    container unit {
                        config false;
                        ze:command "ze-iface:interface-unit-add";
                        ze:rpc "ze-iface-api:interface-unit-add";
                        ze:backend "netlink";
                        description "The VLAN id is 1 to 4094, and the new interface is named
<name>.<vid>. The dummy is created first when it is absent, and deleted again when this step
fails.";
                        ze:help "Add a VLAN sub-interface to the dummy.";
                        leaf name {
                            type string;
                            mandatory true;
                            description "The dummy the unit hangs off. The dispatcher creates it
first when it is absent.";
                            ze:help "Parent interface name";
                        }
                        leaf vid {
                            type zt:vlan-id;
                            mandatory true;
                            description "The 802.1Q tag of the unit. The new device is named
<name>.<vid>, and a tag outside 1 to 4094 is refused before the backend is called.";
                            ze:help "VLAN ID";
                        }
                    }

                    container address {
                        config false;
                        ze:command "ze-iface:interface-addr-add";
                        ze:rpc "ze-iface-api:interface-addr-add";
                        ze:backend "netlink";
                        description "The address is written in CIDR form, for example
10.0.0.1/32. The dummy is created first when it is absent, and deleted again when this step
fails.";
                        ze:help "Add an IP address to the dummy.";
                        leaf name {
                            type string;
                            mandatory true;
                            description "The dummy that receives the address. The dispatcher
creates it first when it is absent.";
                            ze:help "Interface name";
                        }
                        leaf prefix {
                            type ip-prefix;
                            mandatory true;
                            description "An IPv4 or IPv6 address with its prefix length, for
example 10.0.0.1/32. Ze passes the string to the netlink backend.";
                            ze:help "Address in CIDR form";
                        }
                    }
                }
            }

            container veth {
                config false;
                description "One command creates both ends of the pair. veth has no compound
form, so create the pair first, then add a unit or an address to either end.";
                ze:help "Create a veth pair (two linked virtual Ethernet interfaces).";

                container name {
                    config false;
                    ze:command "ze-iface:interface-create-veth";
                    ze:rpc "ze-iface-api:interface-create-veth";
                    ze:backend "netlink";
                    description "The peer name is the second value and is required. A second
create of the same name changes nothing and reports that the pair is present.";
                    ze:help "Create a veth pair (two linked virtual Ethernet interfaces).";
                    leaf name {
                        type string;
                        mandatory true;
                        description "The name of the first end of the pair. A pair already
present under that name is reported, and nothing changes.";
                        ze:help "Interface name";
                    }
                    leaf peer {
                        type string;
                        mandatory true;
                        description "The name of the second end. Both ends appear in the kernel
after the one command.";
                        ze:help "Peer interface name";
                    }
                }
            }

            container bridge {
                config false;
                description "A second create of the same name changes nothing and reports that
the bridge is present. It fails when that name holds an interface of another type.";
                ze:help "Create a Linux bridge for L2 forwarding.";

                container name {
                    config false;
                    ze:command "ze-iface:interface-create-bridge";
                    ze:backend "netlink";
                    ze:ensure-exists "ze-iface:interface-delete";
                    description "The command is idempotent. When a unit or address command under
it fails, and this command created the bridge, the bridge is deleted again.";
                    ze:help "Create a Linux bridge for L2 forwarding.";
                    leaf name {
                        type string;
                        mandatory true;
                        description "The name of the bridge to create. A name that holds an
interface of another type is refused, and the error names both types.";
                        ze:help "Interface name";
                    }

                    container unit {
                        config false;
                        ze:command "ze-iface:interface-unit-add";
                        ze:rpc "ze-iface-api:interface-unit-add";
                        ze:backend "netlink";
                        description "The VLAN id is 1 to 4094, and the new interface is named
<name>.<vid>. The bridge is created first when it is absent, and deleted again when this
step fails.";
                        ze:help "Add a VLAN sub-interface to the bridge.";
                        leaf name {
                            type string;
                            mandatory true;
                            description "The bridge the unit hangs off. The dispatcher creates
it first when it is absent.";
                            ze:help "Parent interface name";
                        }
                        leaf vid {
                            type zt:vlan-id;
                            mandatory true;
                            description "The 802.1Q tag of the unit. The new device is named
<name>.<vid>, and a tag outside 1 to 4094 is refused before the backend is called.";
                            ze:help "VLAN ID";
                        }
                    }

                    container address {
                        config false;
                        ze:command "ze-iface:interface-addr-add";
                        ze:rpc "ze-iface-api:interface-addr-add";
                        ze:backend "netlink";
                        description "The address is written in CIDR form, for example
10.0.0.1/32. The bridge is created first when it is absent, and deleted again when this step
fails.";
                        ze:help "Add an IP address to the bridge.";
                        leaf name {
                            type string;
                            mandatory true;
                            description "The bridge that receives the address. The dispatcher
creates it first when it is absent.";
                            ze:help "Interface name";
                        }
                        leaf prefix {
                            type ip-prefix;
                            mandatory true;
                            description "An IPv4 or IPv6 address with its prefix length, for
example 10.0.0.1/32. Ze passes the string to the netlink backend.";
                            ze:help "Address in CIDR form";
                        }
                    }
                }
            }

            container unit {
                config false;
                ze:command "ze-iface:interface-unit-add";
                ze:rpc "ze-iface-api:interface-unit-add";
                description "The parent interface must already exist.";
                ze:help "Add a VLAN sub-interface (802.1Q tagged).";
                leaf name {
                    type string;
                    mandatory true;
                    description "The parent interface. This form creates no interface, so
the name must be present in the kernel before the command runs.";
                    ze:help "Parent interface name";
                }
                leaf vid {
                    type zt:vlan-id;
                    mandatory true;
                    description "The 802.1Q tag of the unit. The new device is named
<name>.<vid>, and a tag outside 1 to 4094 is refused before the backend is called.";
                    ze:help "VLAN ID";
                }
            }

            container address {
                config false;
                ze:command "ze-iface:interface-addr-add";
                ze:rpc "ze-iface-api:interface-addr-add";
                description "The interface must already exist.";
                ze:help "Add an IP address to an interface.";
                leaf name {
                    type string;
                    mandatory true;
                    description "The interface that receives the address. This form creates
no interface, so the name must be present in the kernel before the command runs.";
                    ze:help "Interface name";
                }
                leaf prefix {
                    type ip-prefix;
                    mandatory true;
                    description "An IPv4 or IPv6 address with its prefix length, for example
10.0.0.1/24. Ze passes the string to the netlink backend.";
                    ze:help "Address in CIDR form";
                }
            }
        }
    }

    container delete {
        config false;

        container interface {
            config false;
            description "Every form takes the interface name first. Ze translates that name to
its kernel device, so a name bound to hardware by a selector reaches the right port.";
            ze:help "Delete an interface, unit, or address.";

            container name {
                config false;
                ze:command "ze-iface:interface-delete";
                ze:rpc "ze-iface-api:interface-delete";
                description "The dispatcher calls this same command to undo a compound create.
An interface it created is deleted when the unit or address step after it fails.";
                ze:help "Delete an interface from the kernel.";
                leaf name {
                    type string;
                    mandatory true;
                    description "The interface to delete. The unit and address forms below
keep this interface and remove one unit or one address of it.";
                    ze:help "Interface name";
                }

                container unit {
                    config false;
                    ze:command "ze-iface:interface-unit-del";
                    ze:rpc "ze-iface-api:interface-unit-del";
                    description "The VLAN id is 1 to 4094. The interface deleted is
<name>.<vid>, so the parent interface stays.";
                    ze:help "Remove a VLAN sub-interface.";
                    leaf name {
                        type string;
                        mandatory true;
                        description "The parent interface. Ze joins it with the VLAN id into
<name>.<vid> and deletes that device.";
                        ze:help "Parent interface name";
                    }
                    leaf vid {
                        type zt:vlan-id;
                        mandatory true;
                        description "The 802.1Q tag of the unit to remove. A tag outside 1 to
4094 is refused before the backend is called.";
                        ze:help "VLAN ID";
                    }
                }

                container address {
                    config false;
                    ze:command "ze-iface:interface-addr-del";
                    ze:rpc "ze-iface-api:interface-addr-del";
                    description "Give the address in the same CIDR form it was added with. The
interface stays, and only that address goes.";
                    ze:help "Remove an IP address from an interface.";
                    leaf name {
                        type string;
                        mandatory true;
                        description "The interface that holds the address. Its other addresses
stay.";
                        ze:help "Interface name";
                    }
                    leaf prefix {
                        type ip-prefix;
                        mandatory true;
                        description "An IPv4 or IPv6 address with its prefix length. Ze passes
the string to the netlink backend, so it must match the string the add used.";
                        ze:help "Address in CIDR form";
                    }
                }
            }
        }
    }

    container request {
        config false;

        container interface {
            config false;
            description "The interface name is given once, after this keyword, and every command
below it uses that name. request interface migrate is the exception, because it names two
interfaces of its own.";
            ze:help "Interface operational state.";

            // The interface every command below acts on. It is declared here,
            // on the keyword the operator types it after, and each of those
            // commands inherits it.
            leaf name {
                type string;
                mandatory true;
                description "The interface that up, down, mtu and mac act on. Each of those
commands inherits it, and migrate names its own interfaces instead.";
                ze:help "Interface name";
            }

            container up {
                config false;
                ze:command "ze-iface:interface-up";
                description "Only the administrative state changes. show interface reports the
operational state, which a dummy, bridge or veth reports as unknown rather than up.";
                ze:help "Bring an interface up.";
            }

            container down {
                config false;
                ze:command "ze-iface:interface-down";
                description "Only the administrative state changes. A name bound to hardware by
a selector is refused when the selector resolves to no device, so the shutdown cannot reach
another port.";
                ze:help "Shut down an interface.";
            }

            container mtu {
                config false;
                ze:command "ze-iface:interface-mtu";
                description "The MTU is between 68 and 65535 bytes.";
                ze:help "Set the MTU on an interface.";
                leaf bytes {
                    type uint16 { range "68..65535"; }
                    mandatory true;
                    description "The largest frame payload the interface accepts. A value
outside 68 to 65535 is refused before the backend is called.";
                    ze:help "MTU in bytes";
                }
            }

            container mac {
                config false;
                ze:command "ze-iface:interface-mac";
                description "The address is written as xx:xx:xx:xx:xx:xx. Ze checks that form
before it calls the backend, so a malformed address is refused with its own message.";
                ze:help "Set the MAC address on an interface.";
                leaf address {
                    type string { pattern '[0-9a-fA-F]{2}(:[0-9a-fA-F]{2}){5}'; }
                    mandatory true;
                    description "Six hexadecimal byte pairs separated by colons, in either
case. The kernel device takes this address in place of the one it has.";
                    ze:help "MAC address, as xx:xx:xx:xx:xx:xx";
                }
            }

            container migrate {
                config false;
                ze:command "ze-iface:interface-migrate";
                ze:rpc "ze-iface-api:interface-migrate";
                ze:inherit "none";
                description "Takes a source interface, a target interface, and the
address to move. Adds addresses to the target before removing them from the
source (make-before-break).";
                ze:help "Move IP addresses between interfaces with minimal downtime.";

                container from {
                    config false;
                    ze:modifier "required";
                    description "The value is an interface and one of its units, written as
name.unit. Unit 0 is the interface itself.";
                    ze:help "Interface and unit the address moves off.";
                    leaf source {
                        type iface-unit;
                        mandatory true;
                        description "Written as name.unit, where unit 0 is the interface
itself. The address leaves this unit in phase 4, after BGP confirms it is ready on the
destination.";
                        ze:help "Source interface and unit";
                    }
                }

                container to {
                    config false;
                    ze:modifier "required";
                    description "The value is an interface and one of its units, written as
name.unit. The address is added here before it is removed from the source.";
                    ze:help "Interface and unit the address moves onto.";
                    leaf destination {
                        type iface-unit;
                        mandatory true;
                        description "Written as name.unit, where unit 0 is the interface
itself. The address is added to this unit in phase 2, before it leaves the source.";
                        ze:help "Destination interface and unit";
                    }
                }

                container address {
                    config false;
                    ze:modifier "required";
                    description "One address moves for each command, written in CIDR form. Each
keyword of migrate is given once, and a second one is refused.";
                    ze:help "Address to move.";
                    leaf prefix {
                        type ip-prefix;
                        mandatory true;
                        description "An IPv4 or IPv6 address with its prefix length. The BGP
readiness wait matches on the address part alone, because BGP binds to the address and
not the prefix.";
                        ze:help "Address in CIDR form";
                    }
                }

                container create {
                    config false;
                    ze:modifier "once";
                    description "Leave it out when the destination interface
exists.";
                    ze:help "Create the destination interface before the address moves onto it.";
                    leaf type {
                        type enumeration {
                            enum dummy { ze:help "Create the destination as a dummy interface."; }
                            enum veth { ze:help "Create the destination as a veth pair, its peer named <name>-peer."; }
                            enum bridge { ze:help "Create the destination as a Linux bridge."; }
                        }
                        mandatory true;
                        description "The kind of interface phase 1 creates under the destination
name. A failure in a later phase deletes the interface this phase created.";
                        ze:help "Interface type to create";
                    }
                }

                container timeout {
                    config false;
                    ze:modifier "once";
                    description "The wait is for BGP on the destination address.
The default is 30 seconds.";
                    ze:help "How long to wait for BGP to become ready before the move is abandoned.";
                    leaf duration {
                        type duration;
                        mandatory true;
                        description "A number and a unit, for example 30s or 2m. When BGP
reports no listener on the destination address inside this time, the address is removed
from the destination again and the source keeps it.";
                        ze:help "Wait time, as a number and a unit";
                    }
                }
            }
        }
    }
}
