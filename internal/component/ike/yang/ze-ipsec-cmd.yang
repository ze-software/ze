module ze-ipsec-cmd {
    namespace "urn:ze:ipsec:cmd";
    prefix ipseccmd;
    import ze-extensions { prefix ze; }
    // Removing the IPsec surface removes these command nodes together with the
    // handlers. See ai/rules/plugin-self-containment.md.
    description "The show, monitor, and clear vpn ipsec command tree, owned by the ike component.";
    revision 2026-10-17 { description "clear vpn ipsec sa alone is refused: clear vpn ipsec sa all terminates every SA, and clear vpn ipsec sa peer <name> one peer's."; }
    revision 2026-08-03 { description "Added show vpn ipsec dataplane sa/policy/drift: the kernel read-back surface."; }
    revision 2026-06-03 { description "Relocated show + monitor + clear vpn ipsec out of central schemas (plugin self-containment)."; }

    container show {
        config false;
        ze:help "Read-only commands to inspect system, protocol, and network state.";

        container vpn {
            config false;
            description "It reads what is established now. Use monitor vpn to watch the transitions that
                         led there.";
            ze:help "VPN tunnel state (IPsec).";

            container ipsec {
                config false;
                description "The three views are different layers of one tunnel. The peer is the IKE
                             session. The tunnel is the negotiated pair, and the SA is what the
                             kernel installed.";
                ze:help "IPsec SAs, tunnels, and peer connections.";

                container sa {
                    config false;
                    ze:command "ze-ike:show-vpn-ipsec-sa";
                    description "Lists every SA with peer, negotiated algorithms,
byte counts, rekey timers, and uptime. Includes SPIs, NAT detection, and child
SA traffic selectors. It is the main IPsec status command.";
                    ze:help "Show all IKE and Child Security Associations.";
                }

                container status {
                    config false;
                    ze:command "ze-ike:show-vpn-ipsec-status";
                    description "Reports whether the IKE engine is running, how many
peers are configured, and how many IKE SAs are Established.";
                    ze:help "Quick IPsec health check.";
                }

                container dataplane {
                    config false;
                    description "Every other command in this tree reports what the
IKE engine believes it installed. These commands read the kernel instead, so a
kernel expiry, an external flush, or a stranded policy becomes visible.";
                    ze:help "Kernel dataplane state, read back from the forwarding plane.";

                    container sa {
                        config false;
                        ze:command "ze-ike:show-vpn-ipsec-dataplane-sa";
                        description "Lists each installed ESP SA with its SPI,
addresses, mode, algorithms, replay window, byte and packet counters, and
timestamps. Give 'spi <spi>' to show all matching SAs. Without a selector the command
dumps every SA, which on a device with many tunnels is one row per SA.";
                        ze:help "Show the Security Association Database the kernel holds.";
                        // RFC 4303 Section 2.1 reserves SPI 0 and the range 1 to
                        // 255, so 0 is not a valid selector and the command
                        // refuses it.
                        leaf spi {
                            type uint32 {
                                range "1..4294967295";
                            }
                            description "The value is decimal. Ze keeps only the SAs whose SPI equals it, and
the inbound SA and the outbound SA of one tunnel carry different SPIs, so one value
names one direction. The value 0 is refused.";
                            ze:help "Show all SAs with this SPI.";
                        }
                    }

                    container policy {
                        config false;
                        ze:command "ze-ike:show-vpn-ipsec-dataplane-policy";
                        description "Lists each policy with its selector prefixes
and ports, direction, priority, upper-layer protocol, if_id, interface index,
tunnel endpoints, and the peer that installed it. Each policy also names the SPD
that holds it (spd: node for if_id 0, the bound XFRM interface, or if-id and the
number) and the job Ze installed it for (role), which reads unknown for a policy
Ze did not install. A per-socket policy, which overrides every SPD entry for its one
socket, reads spd socket, its direction in, out or fwd, and role esp-form-socket for
Ze's own ESP form reader or socket-override for any other process's. A policy with no matching SA is the failure
this command exists to show. RFC 4301 Section 4.4 keeps the SPD and the SAD
separate, and so does this tree.";
                        ze:help "Show the Security Policy Database the kernel holds.";
                    }

                    container drift {
                        config false;
                        ze:command "ze-ike:show-vpn-ipsec-dataplane-drift";
                        description "Reports each Child SA the engine counts as
installed whose expected identity the kernel SAD does not hold. The command exits non-zero
when it finds drift, so a script CAN test it. A rekey window holds two SPIs and
is not drift.";
                        ze:help "Compare what the IKE engine believes against what the kernel holds.";
                    }
                }

                container peer {
                    config false;
                    description "This is the IKE layer, so it reports the negotiation and the authentication rather
                                 than the traffic selectors the kernel enforces.";
                    ze:help "IPsec peer detail.";

                    container name {
                        config false;
                        ze:command "ze-ike:show-vpn-ipsec-peer";
                        description "Returns IKE SA state, all child SAs with
traffic selectors, and byte counts.";
                        ze:help "Show full detail for one IPsec peer.";
                        leaf name {
                            type string;
                            mandatory true;
                            description "The value is the key of a site-to-site peer entry, at most 255
characters. Ze returns every IKE SA that peer holds, and answers 'peer not found' when
none is up.";
                            ze:help "Configured IPsec peer name.";
                        }
                    }
                }
            }
        }
    }

    container clear {
        config false;

        container vpn {
            config false;
            description "Clearing stops the security association and leaves the configuration alone.
                         A tunnel configured to re-establish WILL negotiate a new SA.";
            ze:help "VPN tunnel clearing operations.";

            container ipsec {
                config false;
                description "The SA is removed from the kernel and from Ze. Traffic that matched its
                             selector is no longer encrypted, and it does not revert to plaintext.";
                ze:help "IPsec SA teardown.";

                container sa {
                    config false;
                    description "Clear vpn ipsec sa alone is refused: say all to terminate every
SA, or peer followed by a name to terminate one peer's. Everything is never the default
(ai/rules/cli.md). A tunnel whose config is still active WILL renegotiate.";
                    ze:help "Tear down IKE Security Associations: all, or peer <name>.";

                    container all {
                        config false;
                        ze:command "ze-ike:clear-vpn-ipsec-sa";
                        description "Every IKE SA and its Child SAs are terminated, and the answer
counts them. Each tunnel whose config is still active WILL renegotiate.";
                        ze:help "Tear down every IKE Security Association.";
                    }

                    container peer {
                        config false;
                        ze:command "ze-ike:clear-vpn-ipsec-sa-peer";
                        description "Only the named peer's SAs are terminated. A name that matches
no configured peer is refused.";
                        ze:help "Tear down one peer's IKE Security Associations.";
                        leaf name {
                            type string {
                                length "1..255";
                            }
                            mandatory true;
                            description "The peer name as configured under the IPsec connection.";
                            ze:help "Peer name.";
                        }
                    }
                }
            }
        }
    }

    container monitor {
        config false;
        ze:help "Continuous monitoring commands (Ctrl-C to stop).";

        container vpn {
            config false;
            description "The stream follows the tunnel while it negotiates, rekeys and stops. It is
                         a live feed, and show vpn gives the current-state view.";
            ze:help "VPN event streams.";

            container ipsec {
                config false;
                ze:command "ze-ike:monitor-vpn-ipsec";
                ze:task-support required;
                description "Streams sa-up, sa-down, child-up, child-down, and
child-rekey events. Use it to debug a tunnel flap or a rekey problem.";
                ze:help "Watch IPsec SA events as they happen.";
            }
        }
    }
}
