module ze-ipsec-conf {
    namespace "urn:ze:ipsec:conf";
    prefix ipsec;

    import ze-extensions { prefix ze; }
    import ze-types { prefix zt; }

    description "IPsec VPN configuration for Ze (spec-ipsec-3).";

    revision 2026-05-20 {
        description "Initial IPsec data model: ESP/IKE groups, site-to-site peers.";
    }

    typedef encryption-algo {
        type enumeration {
            enum aes128 { ze:help "AES-CBC-128 (RFC 3602)."; }
            enum aes256 { ze:help "AES-CBC-256 (RFC 3602)."; }
            enum aes128gcm { ze:help "AES-GCM-128, 16-byte ICV (RFC 4106)."; }
            enum aes256gcm { ze:help "AES-GCM-256, 16-byte ICV (RFC 4106)."; }
            enum aes128ccm8 {
                ze:help "AES-CCM-128, 8-byte ICV (RFC 4309, RFC 5282). IKE SA only.";
            }
            enum aes256ccm8 {
                ze:help "AES-CCM-256, 8-byte ICV (RFC 4309, RFC 5282). IKE SA only.";
            }
            enum aes128ccm12 {
                ze:help "AES-CCM-128, 12-byte ICV (RFC 4309, RFC 5282). IKE SA only.";
            }
            enum aes256ccm12 {
                ze:help "AES-CCM-256, 12-byte ICV (RFC 4309, RFC 5282). IKE SA only.";
            }
            enum aes128ccm16 {
                ze:help "AES-CCM-128, 16-byte ICV (RFC 4309, RFC 5282). IKE SA only.";
            }
            enum aes256ccm16 {
                ze:help "AES-CCM-256, 16-byte ICV (RFC 4309, RFC 5282). IKE SA only.";
            }
            enum chacha20poly1305 {
                ze:help "ChaCha20-Poly1305 AEAD (RFC 7634). ESP only; omit hash.";
            }
            enum 3des {
                ze:help "Triple-DES-CBC (RFC 2451), legacy ESP only; requires hash.";
            }
            enum null {
                ze:help "NULL encryption (RFC 2410): integrity-only ESP, which needs a hash. ESP only.";
            }
        }
    }

    typedef hash-algo {
        type enumeration {
            enum sha1 {
                ze:help "HMAC-SHA-1-96 (RFC 2404), legacy ESP integrity only; not an IKE PRF.";
            }
            enum sha256 { ze:help "HMAC-SHA-256-128 (RFC 4868)."; }
            enum sha384 { ze:help "HMAC-SHA-384-192 (RFC 4868)."; }
            enum sha512 { ze:help "HMAC-SHA-512-256 (RFC 4868)."; }
        }
    }

    container vpn {
        description "Ze declares one subsystem under it today, which is ipsec. That subsystem holds the ESP
            groups, the IKE groups and the site-to-site peers.";
        ze:help "VPN subsystems.";

        container ipsec {
            description "Ze speaks IKEv2 (RFC 7296) and installs each negotiated Child SA into the Linux XFRM
                stack. A peer references one ESP group and one IKE group, and those two carry the
                algorithms and the timers of the tunnel.";
            ze:help "IPsec VPN configuration.";

            leaf interface {
                type string;
                description "Commit accepts a name no interface on the host carries yet, so a WAN created
                    after Ze (a PPPoE unit) can be named; the doctor check ipsec-interface reports
                    a name the host does not hold. The first IPv4 address of the interface fills the local-address of every peer that names none, and Ze
                    follows it: when an address appears (a PPPoE or DHCP WAN that came up after
                    Ze), those peers start; when it changes, they restart from the new address;
                    when it leaves, they stop and remove their Child SAs, and wait. The IKE socket
                    on port 500 binds there. The NAT-T socket on port 4500 also binds there unless
                    live XFRM migration is available, when it listens on the wildcard and selects
                    each SA's source address explicitly. A peer with its own local-address keeps
                    its own socket and is never restarted by an interface address event. A reload
                    whose interface holds no IPv4 address is refused, and the same case at startup
                    runs, writes a warning, and the doctor check ipsec-interface-address names the
                    waiting peers.";
                ze:help "WAN interface for IPsec traffic.";
            }

            leaf cookie-threshold {
                type uint32;
                default 0;
                description "Number of half-open IKE SAs tolerated before an inbound
                             IKE_SA_INIT must answer a COOKIE challenge. RFC 7296
                             Section 2.6 makes the challenge the answer to state and CPU
                             exhaustion from forged source addresses. The default of 0
                             challenges every inbound initiation, which costs one extra
                             round trip and stops a single spoofed datagram taking a
                             peer's only half-open handshake slot. Raise it to tolerate
                             that many half-open handshakes before challenging.";
                ze:help
                    "Number of half-open IKE SAs tolerated before a COOKIE challenge.";
            }

            leaf unmatched {
                type enumeration {
                    enum discard {
                        ze:help "Discard traffic no SPD entry matches (RFC 4301 Section 5).";
                    }
                    enum bypass {
                        ze:help "Pass traffic no SPD entry matches in the clear.";
                    }
                }
                default discard;
                description "The disposition of the catch-all entry Ze installs last in the
                             Security Policy Database, in every direction and for both address
                             families. RFC 4301 Section 5: 'If no policy is found in the SPD
                             that matches a packet (for either inbound or outbound traffic),
                             the packet MUST be discarded.' The catch-all is that policy, so
                             a packet no other entry names always meets one.

                             The default is discard, the entry RFC 4301 Section 4.4.1 asks
                             for: 'Every SPD SHOULD have a nominal, final entry that matches
                             anything that is otherwise unmatched, and discards it.' It also
                             drops the router's own traffic where it crosses in the clear:
                             BGP, SSH, DNS, NTP, ICMP (ping, traceroute, show mtu probes and
                             path-MTU errors) and IPv6 neighbor discovery, which is ICMPv6
                             (protocol 58). So write a bypass entry under
                             policy for every flow that must still cross in the clear, or set
                             bypass to pass all of it. A commit that would turn the discard
                             on while this leaf is unset is refused until the leaf is
                             written. The IKE control plane keeps its own bypass at order 100
                             either way.

                             bypass carries ICMP errors in clear, and Linux would still send
                             one about a tunnelled packet into the Child SA of a site-to-site
                             peer whose icmp-error-check is true, so commit refuses bypass
                             beside such a peer; set icmp-error-check false on it. An ICMP
                             bypass entry under policy meets the same refusal. A peer with
                             vti bind is exempt: its Child SA policies carry the xfrm
                             interface's if_id, which the kernel's error mapping never
                             looks up.";
                ze:help "Disposition of traffic no SPD entry matches: discard or bypass.";
            }

            leaf application-override {
                type enumeration {
                    enum deny {
                        ze:help "Refuse every per-socket IPsec policy but Ze's own.";
                    }
                    enum allow {
                        ze:help "Let any process holding CAP_NET_ADMIN set per-socket IPsec policies.";
                    }
                }
                default deny;
                description "Whether a user or application may override this Security Policy
                             Database. RFC 4301 Section 4.4.1: 'However, the system
                             administrator MUST be able to specify whether or not a user or
                             application can override (default) system policies.' On Linux an
                             application overrides the SPD by setting a per-socket policy
                             (IP_XFRM_POLICY, IPV6_XFRM_POLICY and the IPSEC_POLICY
                             spellings), which outranks every SPD entry, the discard
                             catch-all included.

                             deny attaches a setsockopt guard to the cgroup2 root that refuses
                             those four options with EPERM to every process in Ze's network
                             namespace except Ze's own IPsec dataplane, so it needs ze to hold
                             CAP_BPF and CAP_NET_ADMIN, a cgroup2 mount and Linux 6.10 or
                             later; a guard that
                             cannot attach fails the commit. allow attaches nothing, and Linux
                             lets any process holding CAP_NET_ADMIN set one. A process holding
                             CAP_NET_ADMIN can still write the SPD itself, which no setsockopt
                             guard sees: ze doctor names every such process.";
                ze:help "Whether applications may override the SPD per socket: deny or allow.";
            }

            list policy {
                key "name";
                description "An entry of the Security Policy Database that Ze installs directly,
                             rather than one a Child SA negotiation produces.

                             RFC 4301 Section 4.4.1 gives the database three dispositions:
                             'PROTECT, BYPASS, or DISCARD'. A peer under site-to-site produces
                             the PROTECT entries, because those name a transform and a peer to
                             negotiate it with. The other two name neither, so they are written
                             here: BYPASS lets traffic cross the IPsec boundary in the clear,
                             and DISCARD stops it at the boundary.

                             Section 7.4 makes the discard disposition an obligation: 'All
                             implementations MUST support DISCARDing of fragments using the
                             normal SPD packet classification mechanisms.' This list is the
                             management interface that Section 4.4.1 requires for it.

                             Ze installs every entry when the configuration is applied and
                             removes it when the entry leaves the configuration. An entry needs
                             no peer, no key and no negotiation, so it is in force whether or
                             not any tunnel is up.";
                ze:help
                    "Operator-authored Security Policy Database entry.";

                leaf name {
                    type string {
                        length "1..64";
                        pattern '[a-zA-Z0-9][a-zA-Z0-9_.-]*';
                    }
                    description "The name identifies the entry in the configuration and in the output of
                        `show vpn ipsec dataplane`. It does not reach the kernel, which identifies a
                        policy by its selector alone, so two entries whose selector, direction and
                        order all agree describe one kernel policy and commit refuses the pair.";
                    ze:help "Entry name, unique across the Security Policy Database.";
                }

                leaf action {
                    type enumeration {
                        enum bypass {
                            ze:help "Let matching traffic cross the boundary unprotected.";
                        }
                        enum discard {
                            ze:help "Drop matching traffic at the boundary.";
                        }
                    }
                    mandatory true;
                    description "RFC 4301 Section 4.4.1 defines bypass as 'to allow the packet to pass
                                 without IPsec protection' and discard as 'to discard the traffic, i.e.,
                                 not to let the traffic traverse the IPsec boundary'.

                                 There is no protect here on purpose. A protect entry names an ESP
                                 transform, a mode and a peer to negotiate keys with, and those live
                                 under site-to-site peer. Offering the word in both places would put one
                                 concept in two grammars.

                                 The leaf is mandatory rather than defaulted. A defaulted disposition is
                                 the one field of this entry whose wrong value is silent: a bypass
                                 written where a discard was meant passes exactly the traffic the
                                 operator wrote the entry to stop.";
                    ze:help
                        "What the entry does with the traffic its selector matches.";
                }

                leaf order {
                    type uint32 {
                        range "101..2147483647";
                    }
                    default 1000;
                    description "Where this entry sits in the operator's ordering of the Security
                                 Policy Database. A LOWER value is searched FIRST, in Ze and in the
                                 Linux kernel, and it carries the same meaning as policy-priority
                                 under a site-to-site peer.

                                 RFC 4301 Section 4.4.1: the management interface 'MUST support
                                 (total) ordering of these entries, as seen via this interface'.

                                 The default of 1000 sits between the IKE control-plane bypass at 100
                                 and a peer's default rank of 2000, so an entry written with no order
                                 outranks the tunnels and carves its hole out of them. Raise it above
                                 2000 to let a tunnel win instead.

                                 The range starts above 100 for the reason policy-priority states: an
                                 entry at or above the IKE bypass captures the IKE exchange that
                                 builds and rekeys every tunnel on the node.";
                    ze:help
                        "Rank of this entry, lowest searched first.";
                }

                leaf direction {
                    type enumeration {
                        enum out {
                            ze:help "Traffic leaving for the unprotected side.";
                        }
                        enum in {
                            ze:help "Traffic arriving from the unprotected side.";
                        }
                        enum both {
                            ze:help "Both directions, as a mirrored pair of entries.";
                        }
                    }
                    default both;
                    description "RFC 4301 Section 4.4.1 splits the database by direction: SPD-O holds
                                 the outbound bypass and discard entries and SPD-I holds the inbound
                                 ones. A policy is one-way, so a Ze entry is one-way too.

                                 both installs the mirrored pair: the outbound entry keeps local and
                                 remote as written, and the inbound entry swaps them, because the local
                                 side of a flow is the DESTINATION of an inbound packet. It is the
                                 default because a one-way discard leaves the return traffic crossing
                                 the boundary, which almost never expresses what the operator meant.";
                    ze:help
                        "Which side of the boundary the entry acts on.";
                }

                leaf protocol {
                    type uint8;
                    default 0;
                    description "The next-layer protocol of RFC 4301 Section 4.4.1.1, such as 6 for TCP
                                 and 17 for UDP. Zero is that section's ANY, which matches every
                                 protocol.

                                 A local-port or remote-port other than any needs this leaf to name a
                                 protocol that carries ports. Commit refuses the pair otherwise,
                                 because a port selector under protocol 0 would match on a field the
                                 classifier cannot read.";
                    ze:help
                        "IP protocol number the selector matches, 0 for every protocol.";
                }

                leaf icmp-type {
                    type union {
                        type uint8;
                        type enumeration {
                            enum any {
                                ze:help "Every ICMP message type.";
                            }
                        }
                    }
                    default any;
                    description "The ICMP message type of RFC 4301 Section 4.4.1.1: 'If the Next Layer
                                 Protocol value is ICMP, then there is a 16-bit selector for the ICMP
                                 message type and code.' It needs protocol 1 (ICMP) or 58 (ICMPv6), and
                                 commit refuses it under any other protocol or beside a port other
                                 than any.

                                 An ICMP message has one type whichever way it travels, so a both entry
                                 installs the same type in each direction. With action discard and
                                 direction in, the entry rejects that type of ICMP arriving in the
                                 clear at this node from the remote prefix: the per-type control of
                                 RFC 4301 Sections 6.1.1 and 6.1.2.

                                 An ICMP message arriving on a Child SA is decided by that SA's peer
                                 on Linux. When its icmp-error-check is true (the default), the
                                 kernel delivers a message this entry refuses whenever the header the
                                 message carries after its ICMP header, with addresses and ports
                                 reversed, matches the SA it arrived on, whatever the ICMP type. So
                                 commit refuses a discard entry, in or both, matching ICMP in a family
                                 such a peer's selectors carry, whatever its type and prefixes. In the
                                 other direction the kernel sends an ICMP error this router generates
                                 into a Child SA of such a peer even where a bypass entry would carry
                                 it in clear, so commit refuses a bypass entry, out or both, with type
                                 any or an ICMP error type (IPv4 3, 4, 5, 11, 12; IPv6 1, 2, 3, 4:
                                 the types Linux 7.3 sends through its return-SA lookup, listed in
                                 icmp_overlap.go) and a remote prefix overlapping that peer's remote
                                 selectors. With icmp-error-check false on that peer, this entry
                                 decides. A peer with vti bind meets neither refusal: its Child SA
                                 policies carry the xfrm interface's if_id, which neither kernel
                                 path compares with this entry.

                                 The VPP dataplane compares no ICMP type or code, so it refuses an
                                 entry that names one rather than matching every ICMP message.

                                 Linux classifies every IP fragment as type 0 code 0, and it
                                 classifies forwarded traffic before reassembling it, so commit
                                 refuses type 0 with an icmp-code that includes 0 on an out or both
                                 entry: its outbound half would also take every forwarded ICMP
                                 fragment between the prefixes. Use direction in, or an icmp-code
                                 range starting at 1.";
                    ze:help
                        "ICMP message type the selector matches, or any.";
                }

                leaf icmp-code {
                    type union {
                        type uint8;
                        type string {
                            pattern '[0-9]{1,3}-[0-9]{1,3}';
                        }
                        type enumeration {
                            enum any {
                                ze:help "Every ICMP code of the type.";
                            }
                        }
                    }
                    default any;
                    description "The ICMP code, one number or an inclusive range written start-end, such
                                 as 0-3. RFC 4301 Section 4.4.1.1 allows 'a single type and a range of
                                 codes, a single type and ANY code, and ANY type and ANY code', so a code
                                 needs icmp-type, and commit refuses a range whose start is above its
                                 end.

                                 The kernel selector matches a value under a mask, so Ze installs a
                                 code range as the fewest mask-aligned blocks that cover exactly that
                                 range, one kernel policy per block, all added and removed together.
                                 No code outside the range matches.";
                    ze:help
                        "ICMP code or start-end code range the selector matches, or any.";
                }

                container local {
                    description "Local is Ze's own side of the IPsec boundary. It is the source of an
                        outbound packet and the destination of an inbound one, which is the swap
                        direction both performs.";
                    ze:help "The local side of the selector.";

                    leaf prefix {
                        type zt:ip-prefix;
                        mandatory true;
                        description "The value is a CIDR prefix and Ze installs it as the local selector of
                            the policy. Use 0.0.0.0/0 or ::/0 for every address. The two prefixes of
                            one entry MUST share an address family, and commit refuses a mixed pair
                            because a kernel selector carries one family.";
                        ze:help "Local traffic the entry matches.";
                    }

                    leaf port {
                        type union {
                            type uint16 { range "1..65535"; }
                            type enumeration {
                                enum any {
                                    ze:help "Every port.";
                                }
                            }
                        }
                        default any;
                        description "One exact port, or any for every port. RFC 4301 Section 4.4.1.1 defines
                            the selector as a list of ranges; the kernel selector Ze programs carries a
                            port and a mask, which expresses every port or one exact port and no
                            range between them. A range is refused rather than widened to any,
                            because widening would bypass or discard traffic the operator did not
                            name.";
                        ze:help "Local port of the selector.";
                    }
                }

                container remote {
                    description "Remote is the far side of the IPsec boundary. It is the destination of an
                        outbound packet and the source of an inbound one.";
                    ze:help "The remote side of the selector.";

                    leaf prefix {
                        type zt:ip-prefix;
                        mandatory true;
                        description "It follows the rules the local prefix states, including the shared
                            address family.";
                        ze:help "Remote traffic the entry matches.";
                    }

                    leaf port {
                        type union {
                            type uint16 { range "1..65535"; }
                            type enumeration {
                                enum any {
                                    ze:help "Every port.";
                                }
                            }
                        }
                        default any;
                        description "It follows the rule the local port states: one exact port or any, and a
                            value other than any needs the protocol leaf.";
                        ze:help "Remote port of the selector.";
                    }
                }
            }

            list esp-group {
                key "name";
                description "The group carries the ESP proposals a peer offers for its Child SAs and the lifetime
                    those SAs run under. A group MUST hold at least one proposal, and commit refuses an
                    empty one. One group holds at most 255 proposals.";
                ze:help "ESP (Encapsulating Security Payload) group.";

                leaf name {
                    type string;
                    description "The name holds 1 to 255 characters from the set a-z, A-Z, 0-9, hyphen,
                        underscore and period. A site-to-site peer references the group by this name.";
                    ze:help "ESP group name.";
                }

                leaf lifetime {
                    type uint32 {
                        range "0..86400";
                    }
                    default 3600;
                    description "The Child SA rekey trigger sits ahead of the lifetime by the larger of a
                        random 10 percent and one retransmit budget. That lead is capped at half the
                        lifetime. RFC 7296 Section 2.8 states the rule. 'When the lifetime of a
                        Security Association expires, the Security Association MUST NOT be used.' Ze
                        therefore tears the SA down at that point, even when a rekey is still in
                        flight. The value 0 starts no rekey and no expiry.";
                    ze:help "SA lifetime in seconds. 0 disables expiry.";
                }

                leaf pfs {
                    type enumeration {
                        enum enable {
                            ze:help "Send a KEi payload and key each replacement Child SA from a fresh Diffie-Hellman secret.";
                        }
                        enum disable {
                            ze:help "Send no KEi and key each replacement Child SA from SK_d alone.";
                        }
                    }
                    default "enable";
                    description "With enable, Ze puts a KEi payload in the CREATE_CHILD_SA request, and the
                        replacement Child SA is keyed from a fresh Diffie-Hellman secret. With disable,
                        Ze sends no KEi, and the replacement is keyed from SK_d alone, so one leaked
                        SK_d reads every replacement Child SA. RFC 7296 Section 2.17 gives both KEYMAT
                        forms. An ESP proposal carries no Diffie-Hellman group of its own, so Ze offers
                        the group the IKE SA already negotiated. The default is enable, and Ze refuses a
                        response that disagrees with what its request carried.";
                    ze:help "Perfect Forward Secrecy for Child SA rekeying.";
                }

                list proposal {
                    key "number";
                    max-elements 255;
                    description "ESP proposal. Lower number = higher priority. One group
                        offers at most 255 proposals, because RFC 7296 Section 3.3.1
                        numbers them in one octet.";
                    ze:help "ESP proposal, where a lower number is a higher priority.";

                    leaf number {
                        type uint16 {
                            range "1..65535";
                        }
                        description "The number is a PRIORITY and it is not the Proposal Num of the wire. Ze
                            sorts the proposals of the group by this number and offers them lowest
                            first. The wire number comes from the position after that sort, which is how
                            the ike-group proposal number behaves as well.";
                        ze:help "Proposal priority number.";
                    }

                    leaf encryption {
                        type encryption-algo;
                        mandatory true;
                        description "chacha20poly1305 selects a fixed 256-bit AEAD key;
                            omit hash. 3des selects a fixed 192-bit DES-EDE key
                            including parity and requires hash. These ciphers are
                            ESP-only. null selects integrity-only ESP, which RFC 4303
                            Section 1 requires to be negotiable. RFC 4303 Section 3.2
                            forbids ESP with neither confidentiality nor integrity, so a
                            null proposal without a hash is refused at commit.";
                        ze:help "Encryption algorithm.";
                    }

                    leaf hash {
                        type hash-algo;
                        description "Integrity algorithm. It is required beside a
                            non-AEAD cipher, and refused beside an AEAD cipher. RFC 7296
                            Section 3.3 gives an AEAD cipher its own integrity, so an ESP
                            proposal offers the integrity transform NONE. An ESP proposal
                            carries no PRF transform, so this leaf never names one.
                            sha1 selects legacy HMAC-SHA-1-96 with a 160-bit key.
                            It is supported for ESP integrity only, not for IKE.";
                        ze:help "Integrity algorithm.";
                    }
                }
            }

            list ike-group {
                key "name";
                description "The group carries the IKE proposals, the IKE SA lifetime and the Dead Peer Detection
                    timers. A group MUST hold at least one proposal, and commit refuses an empty one.
                    One group holds at most 255 proposals.";
                ze:help "IKE (Internet Key Exchange) group.";

                leaf name {
                    type string;
                    description "The name holds 1 to 255 characters from the set a-z, A-Z, 0-9, hyphen,
                        underscore and period. A site-to-site peer references the group by this name.";
                    ze:help "IKE group name.";
                }

                leaf key-exchange {
                    type enumeration {
                        enum ikev1 {
                            ze:help "Accepted and not read: the group still runs IKEv2.";
                        }
                        enum ikev2 {
                            ze:help "IKEv2 (RFC 7296), the version the engine speaks.";
                        }
                    }
                    default "ikev2";
                    description "The default is ikev2 and the engine writes major version 2 into every header
                        it sends. The parser stores the value and no other code reads it, so a group that
                        names ikev1 commits and still runs IKEv2.";
                    ze:help "IKE protocol version.";
                }

                leaf lifetime {
                    type uint32 {
                        range "0..86400";
                    }
                    default 28800;
                    description "Ze rekeys the IKE SA before the lifetime runs out, on the trigger the ESP group
                        lifetime describes. It also rekeys the SA as the message id space nears its
                        ceiling. RFC 7296 Section 2.2 requires that. 'In the unlikely event that Message
                        IDs grow too large to fit in 32 bits, the IKE SA MUST be closed or rekeyed.' The
                        value 0 starts no rekey, so the SA runs until the peer or the operator ends
                        it.";
                    ze:help "IKE SA lifetime in seconds, where 0 starts no rekey.";
                }

                leaf close-action {
                    type enumeration {
                        enum none {
                            ze:help "The default: the session reconnects on a growing backoff.";
                        }
                        enum start {
                            ze:help "Accepted and not read: the session reconnects on a growing backoff.";
                        }
                        enum restart {
                            ze:help "Accepted and not read: the session reconnects on a growing backoff.";
                        }
                    }
                    default "none";
                    description "The default is none. The parser stores the value and no other code reads it,
                        so none, start and restart leave the daemon with the same behavior. A session
                        whose IKE SA the peer deletes tears its Child SA down and reconnects on a growing
                        backoff. The session loop does this after every failure.";
                    ze:help "Action when peer closes the IKE SA.";
                }

                container dead-peer-detection {
                    description "The timers run whether or not this container is present. A peer with no DPD
                        block probes every 30 seconds and waits 120 seconds for the answer. The probe is
                        an empty INFORMATIONAL request, which is the liveness check of RFC 7296 Sections
                        1.4 and 2.4.";
                    ze:help "Dead Peer Detection (DPD) settings (RFC 3706).";

                    leaf action {
                        type enumeration {
                            enum restart {
                                ze:help "Log restart when the peer is dead, then reconnect on a growing backoff.";
                            }
                            enum hold {
                                ze:help "Log hold when the peer is dead, then reconnect on a growing backoff.";
                            }
                            enum clear {
                                ze:help "Log clear when the peer is dead, then reconnect on a growing backoff.";
                            }
                        }
                        default "hold";
                        description "The default is hold. One log line reads the value when the peer is
                            declared dead, and no other code reads it. The three values restart, hold
                            and clear leave the same behavior. Ze deletes the Child SA, ends the
                            session, and reconnects on a growing backoff.";
                        ze:help "Action when DPD detects a dead peer.";
                    }

                    leaf interval {
                        type uint16 {
                            range "1..3600";
                        }
                        default 30;
                        description "Ze sends the next probe this long after the last one, and it sends none
                            while a probe is outstanding. The default is 30 seconds.";
                        ze:help "DPD probe interval in seconds.";
                    }

                    leaf timeout {
                        type uint16 {
                            range "1..3600";
                        }
                        default 120;
                        description "The value bounds the whole liveness budget, so it covers the first probe and
                            every repeat of it. RFC 7296 Section 2.4 allows the verdict only when
                            'repeated attempts to contact it have gone unanswered for a timeout period'.
                            Ze repeats the probe on a growing backoff inside the budget and tears the SA
                            down when the budget runs out. The default is 120 seconds.";
                        ze:help "DPD timeout in seconds before declaring peer dead.";
                    }
                }

                list proposal {
                    key "number";
                    max-elements 255;
                    description "IKE proposal. Lower number = higher priority. One group
                        offers at most 255 proposals, because RFC 7296 Section 3.3.1
                        numbers them in one octet.";
                    ze:help "IKE proposal, where a lower number is a higher priority.";

                    leaf number {
                        type uint16 {
                            range "1..65535";
                        }
                        description "The number is a PRIORITY and it is not the Proposal Num of the wire. Ze
                            sorts the proposals of the group by this number and offers them lowest
                            first. RFC 7296 Section 3.3 sets the wire number. 'The first Proposal in the
                            initiator's SA payload MUST have a Proposal Num of one (1).' Each later one
                            is one greater, so Ze takes that number from the position after the
                            sort.";
                        ze:help "Proposal priority number.";
                    }

                    leaf encryption {
                        type encryption-algo;
                        mandatory true;
                        description "chacha20poly1305 and 3des are ESP-only in this
                            build and are refused here. RFC 7296 Section 5 forbids ENCR_NULL for the IKE
                            SA, so null is refused here too. The refusal lists the
                            algorithms the build does implement for the IKE SA.";
                        ze:help "Encryption algorithm.";
                    }

                    leaf hash {
                        type hash-algo;
                        mandatory true;
                        description "It is required beside
                            every cipher, and an AEAD cipher is no exception. RFC 7296
                            Section 3.3.3 makes the PRF a mandatory transform for an IKE
                            proposal, and this leaf names it. An ESP proposal reads the
                            same leaf as integrity alone, and refuses it beside an AEAD
                            cipher.
                            sha1 is ESP-only integrity in this build and has no IKE
                            PRF, so it is refused here. The refusal lists the
                            algorithms the build implements for IKE.";
                        ze:help "PRF and integrity algorithm.";
                    }

                    leaf dh-group {
                        type uint8 {
                            range "1..31";
                        }
                        mandatory true;
                        description "The number is Transform Type 4 of RFC 7296 Section 3.3.2. That section lists
                            the values current at publication, up to 18, and sends the reader to the
                            IANA registry for later ones. Ze takes 1 to 31 and refuses a group this
                            build carries no transform for. The refusal lists the numbers the build does
                            carry, which stops the reserved Transform ID 0 reaching the wire.";
                        ze:help "Diffie-Hellman group number (RFC 7296 Section 3.3.2).";
                    }
                }
            }

            container remote-access {
                presence "Serve road warrior clients; the IKE group, the ESP group and the authentication mode are then required.";
                description "Every pool is built at each apply and serves the site-to-site respond peers
                    whose virtual-ip-pool leaf names it: Ze answers their CFG_REQUEST with a lease
                    (RFC 7296 Section 2.19). Admission of road warriors from unconfigured sources and the
                    eap-user list are not served yet, so an eap-user authenticates nobody; configure a
                    client as a respond peer with an EAP mode until that service exists.";
                ze:help "Remote access VPN for road warrior clients (EAP).";

                leaf ike-group {
                    type leafref {
                        path "../../ike-group/name";
                    }
                    mandatory true;
                    description "The group MUST be declared under vpn ipsec ike-group, and commit refuses a
                        name no group carries. No other code reads the reference, because no remote
                        access session runs.";
                    ze:help "Reference to an IKE group name.";
                }

                leaf esp-group {
                    type leafref {
                        path "../../esp-group/name";
                    }
                    mandatory true;
                    description "The group MUST be declared under vpn ipsec esp-group, and commit refuses a
                        name no group carries. No other code reads the reference, because no remote
                        access session runs.";
                    ze:help "Reference to an ESP group name.";
                }

                container authentication {
                    description "Ze reads this block with the same parser as the site-to-site peer
                        authentication block, so mode is mandatory here too. A handshake takes its EAP
                        server credentials from the peer block instead, so the mode named here selects no
                        method. The one effect it carries is the warning the daemon writes when it names
                        eap-md5.";
                    ze:help "EAP authentication settings for remote access.";

                    leaf mode {
                        type enumeration {
                            enum eap-tls {
                                ze:help "EAP-TLS, Type 13 (RFC 5216): the client authenticates with a certificate.";
                            }
                            enum eap-mschapv2 {
                                ze:help "EAP-MSCHAPv2: the client proves its password by challenge and response.";
                            }
                            enum eap-md5 {
                                ze:help "EAP MD5-Challenge, Type 4 (RFC 3748 Section 5.4).";
                            }
                        }
                        mandatory true;
                        description "eap-md5 establishes no shared key, and RFC 7296
                            Section 2.16 discourages such a method: EAP methods that do
                            not establish a shared key SHOULD NOT be used, as they are
                            subject to a number of man-in-the-middle attacks. The IKEv2
                            AUTH payloads are then keyed by SK_pi and SK_pr instead of
                            by an EAP MSK. The method authenticates the client to Ze and
                            tells the client nothing about Ze. The daemon writes one
                            warning when this mode is adopted. Use eap-tls or
                            eap-mschapv2 unless the client runs no other method.";
                        ze:help "EAP authentication method.";
                    }

                    container x509 {
                        description "Server certificate references for EAP. Ze parses
                            both leaves and no component reads them today, so neither
                            takes effect. A commit still refuses a name the PKI store does
                            not hold, and the editor completes the store's entries. The
                            leaves a handshake reads are the site-to-site peer ones.";
                        ze:help "Server certificate references for EAP.";

                        leaf ca-certificate {
                            ze:reference "pki-ca";
                            type string;
                            description "A commit refuses a name that is not a ca entry of the PKI store. The trust
                                anchor of a handshake comes from the ca-certificate leaf of the site-to-site
                                peer.";
                            ze:help "Name of the CA certificate in the PKI store.
                                It has no effect today.";
                        }

                        leaf certificate {
                            ze:reference "pki-certificate";
                            type string;
                            description "A commit refuses a name that is not a certificate entry of the PKI store.
                                The certificate a handshake presents comes from the certificate leaf of the
                                site-to-site peer.";
                            ze:help "Name of the server certificate in the PKI store.
                                It has no effect today.";
                        }
                    }
                }

                list pool {
                    key "name";
                    description "Virtual IP pool for client address assignment (IKEv2 Configuration Payload,
                        RFC 7296 Section 2.19). Commit refuses two pools whose ranges overlap, because both
                        could then lease one inner address to two peers (RFC 3948 Section 5.1).";
                    ze:help "Virtual IP pool for client address assignment.";

                    leaf name {
                        type string;
                        description "The name holds 1 to 255 characters from the set a-z, A-Z, 0-9, hyphen,
                            underscore and period, and commit refuses anything else. A peer's
                            virtual-ip-pool leaf names the pool it draws from, and the name labels the pool
                            in every refusal and log line.";
                        ze:help "Pool name.";
                    }

                    leaf range {
                        type string;
                        description "Commit refuses a value that is not a CIDR prefix, and a prefix length
                            outside /8 to /30. The pool leases the addresses of the prefix without the
                            network address and the broadcast address, so a /30 carries two clients. An
                            empty leaf leases no IPv4 address. A client is sent its lease as
                            INTERNAL_IP4_ADDRESS, with this prefix's mask as INTERNAL_IP4_NETMASK when it
                            asks for one.";
                        ze:help "IPv4 CIDR for client addresses (e.g. 10.10.0.0/24). Prefix length /8-/30.";
                    }

                    leaf range6 {
                        type string;
                        description "Commit refuses a value that is not a CIDR prefix, and a prefix length
                            outside /48 to /126. An empty leaf leases no IPv6 address. A client is sent its
                            lease as INTERNAL_IP6_ADDRESS with this prefix length.";
                        ze:help "IPv6 CIDR for client addresses (e.g. fd00::/64). Prefix length /48-/126.";
                    }

                    leaf-list dns {
                        type string;
                        ordered-by user;
                        description "Each entry is one server address, IPv4 or IPv6, and commit refuses a value
                            that is not an address. A client leased an address of one family is sent the
                            servers of that family, as INTERNAL_IP4_DNS or INTERNAL_IP6_DNS (RFC 7296
                            Section 3.15.1), whether or not it asked for them.";
                        ze:help "DNS server pushed to clients via IKEv2 Configuration Payload.";
                    }

                    leaf domain {
                        type string;
                        description "Commit refuses this leaf when it is set. RFC 7296 Section 3.15.1 defines
                            no search-domain attribute, so no value here could reach a client; delete it.";
                        ze:help "Search domain pushed to clients.";
                    }
                }

                list eap-user {
                    key "name";
                    description "One entry holds the credential of one client. Which leaf carries that
                        credential follows the mode of the authentication block: password for
                        eap-mschapv2 and eap-md5, certificate for eap-tls. Ze validates every entry and
                        no handshake reads one, because EAP runs against the credentials of the
                        site-to-site peer.";
                    ze:help "EAP user entry for remote access authentication.";

                    leaf name {
                        type string;
                        description "The name holds 1 to 255 characters from the set a-z, A-Z, 0-9, hyphen,
                            underscore and period, and commit refuses anything else. It is the key of the
                            list, so it is unique. No code compares it against the identity an EAP client
                            sends.";
                        ze:help "Username.";
                    }

                    leaf password {
                        type string;
                        ze:sensitive;
                        description "Ze reads the leaf when the mode of the authentication block is
                            eap-mschapv2 or eap-md5, and ignores it under every other mode. The $9$
                            wrapper is removed and what is left is the password. Commit refuses an empty
                            value under those two modes, because an empty password authenticates every
                            client that guesses the name. The CLI writes the value back $9$-encoded and
                            masks it in the configuration output.";
                        ze:help "User password ($9$-encoded). Required for eap-mschapv2.";
                    }

                    leaf certificate {
                        ze:reference "pki-certificate";
                        type string;
                        description "Ze reads the leaf when the mode of the authentication block is eap-tls,
                            and ignores it under every other mode. Commit refuses an empty value under
                            eap-tls, and a name that is not a certificate entry of the PKI store under any
                            mode.";
                        ze:help "Client certificate name in PKI store. Required for eap-tls.";
                    }
                }
            }

            container site-to-site {
                description "Each peer under it is one tunnel to one remote gateway. A peer carries its own
                    algorithms, its own identity, its own traffic selectors and its own rank in the
                    Security Policy Database.";
                ze:help "Site-to-site VPN peers.";

                list peer {
                    key "name";
                    description "Ze runs one session for each peer. A configuration reload stops and restarts
                        only the peers whose own configuration changed, so a peer left untouched keeps
                        its Child SAs up. A peer MUST reference one IKE group and one ESP group.";
                    ze:help "Remote VPN peer.";

                    leaf name {
                        type string;
                        description "The name holds 1 to 255 characters from the set a-z, A-Z, 0-9, hyphen,
                            underscore and period. Ze asserts the name as its own IKE identity when the
                            authentication local-id leaf is empty. The name also labels the peer in the
                            log and in the show output.";
                        ze:help "Peer name (used as connection identifier).";
                    }

                    leaf ike-group {
                        type leafref {
                            path "../../../ike-group/name";
                        }
                        mandatory true;
                        description "The group MUST be declared under vpn ipsec ike-group, and commit refuses a
                            name no group carries. It supplies the IKE proposals, the IKE SA lifetime
                            and the Dead Peer Detection timers of this peer.";
                        ze:help "Reference to an IKE group name.";
                    }

                    leaf esp-group {
                        type leafref {
                            path "../../../esp-group/name";
                        }
                        mandatory true;
                        description "The group MUST be declared under vpn ipsec esp-group, and commit refuses a
                            name no group carries. It supplies the ESP proposals Ze offers for this
                            peer's Child SAs and the lifetime those SAs run under.";
                        ze:help "Reference to an ESP group name.";
                    }

                    leaf virtual-ip-pool {
                        type string;
                        description "Names a pool declared under vpn ipsec remote-access pool, and commit refuses
                            an empty name and a name no pool carries. The peer MUST then use
                            connection-type respond and MUST send a CFG_REQUEST in IKE_AUTH: Ze leases it an
                            inner address no other peer holds, answers with a CFG_REPLY, narrows the peer's
                            inner traffic selector of every Child SA the peer asks for to that address, and
                            proposes only that address for the peer's side of every Child SA Ze asks for,
                            refusing a wider answer (RFC 7296 Section 2.19, RFC 3948 Section 5.1). A request Ze
                            cannot serve refuses the Child SA with FAILED_CP_REQUIRED or
                            INTERNAL_ADDRESS_FAILURE and keeps the IKE SA. When the peer has traffic
                            selectors, a remote prefix must cover the pool's ranges. A bound peer declines
                            transport mode.";
                        ze:help "Remote-access pool this respond peer leases its inner address from.";
                    }

                    leaf connection-type {
                        type enumeration {
                            enum initiate {
                                ze:help "Start the IKE_SA_INIT exchange toward remote-address.";
                            }
                            enum respond {
                                ze:help "Start nothing and wait for an IKE_SA_INIT whose source is remote-address.";
                            }
                        }
                        default "initiate";
                        description "With `initiate` Ze starts the IKE_SA_INIT exchange toward remote-address.
                            With respond Ze starts nothing and waits. Ze matches an unsolicited
                            IKE_SA_INIT to a respond peer when the source address of the datagram
                            equals its remote-address. A respond peer that names no remote-address
                            therefore matches nothing.";
                        ze:help "Whether to initiate or wait for the remote peer.";
                    }

                    leaf local-address {
                        type string;
                        description "The value is an IP address literal, and commit refuses anything else,
                            an interface name or a keyword such as any included. Leave it out to let
                            the address follow something: under vpn ipsec interface, the first IPv4
                            address of that interface, followed as it changes; without it, the source
                            address the kernel's route to the remote selects, resolved at the start
                            of every connection attempt. On a host with several addresses that
                            source is the route's, and replies to a peer that initiates leave from
                            it too.";
                        ze:help "Local endpoint IP address.";
                    }

                    leaf remote-address {
                        type string;
                        description "An IPv4 literal or a DNS name. An initiating peer resolves it over udp4
                            at the start of every connection attempt, so a name that answers with a
                            new address is dialed there next time, and a name that does not resolve
                            fails the attempt, which is retried with the reconnect backoff (1 s
                            doubling to 60 s). The resolved address is the remote of the IKE SA: the
                            NAT detection hashes of RFC 7296 Section 2.23, the Child SA endpoints and
                            the transport-mode host pair are built from it. IKE over IPv6 is not
                            supported, so an IPv6 literal does not resolve. A respond peer accepts an
                            unsolicited IKE_SA_INIT from this literal, or from any address the name
                            resolved to at the last refresh (every 60 s and after each commit); a
                            datagram never causes a DNS query.";
                        ze:help "Remote endpoint IPv4 address or DNS hostname.";
                    }

                    leaf nat-traversal {
                        type enumeration {
                            enum allow {
                                ze:help "Allow translated paths and ESP-in-UDP when NAT is detected.";
                            }
                            enum prohibit {
                                ze:help "Reject translated paths and protect MOBIKE address updates.";
                            }
                        }
                        default allow;
                        description "Allow preserves the existing NAT traversal policy. Prohibit rejects
                            detected translation before establishing or migrating a Child SA. It includes
                            NO_NATS_ALLOWED in the first IKE_AUTH request and every MOBIKE address
                            update. NAT detection remains available to detect forbidden translation;
                            supporting UDP 4500 does not override this policy. Changing the policy
                            restarts the peer.";
                        ze:help "Whether this peer permits network address translation.";
                    }

                    leaf mode {
                        type enumeration {
                            enum tunnel {
                                ze:help "Encapsulate the whole packet (RFC 4301 tunnel mode).";
                            }
                            enum transport {
                                ze:help "Protect the payload and keep the outer IP header (RFC 4301 transport mode).";
                            }

                        }
                        default tunnel;
                        description "Encapsulation mode for this peer's Child SAs.

                                     RFC 7296 Section 1.3.1 states the default itself: 'Except when
                                     using this option to negotiate transport mode, all Child SAs will
                                     use tunnel mode.' Ze asks for transport mode by sending
                                     USE_TRANSPORT_MODE with the Child SA request, and the peer can
                                     decline. A declined request establishes a tunnel-mode Child SA
                                     unless transport-required is set.

                                     Transport mode constrains the traffic selectors. RFC 7296 Section
                                     2.23.1 requires exactly one IP address in TSi and in TSr, so every
                                     traffic-selector prefix under this peer must be a single host, and
                                     a vti binding is refused because an XFRM interface carries tunnel
                                     encapsulation.";
                        ze:help
                            "Encapsulation mode for this peer's Child SAs.";
                    }

                    leaf transport-required {
                        type boolean;
                        default false;
                        description "Whether a peer that declines transport mode is unacceptable.

                                     RFC 7296 Section 1.3.1: 'If the responder declines the request, the
                                     Child SA will be established in tunnel mode. If this is unacceptable
                                     to the initiator, the initiator MUST delete the SA.' Only the
                                     operator knows whether it is unacceptable, so this leaf carries that
                                     decision. When it is true and the response omits USE_TRANSPORT_MODE,
                                     Ze deletes the SA rather than run a tunnel-mode Child SA the
                                     operator did not ask for. When it is false the SA stays up in
                                     tunnel mode, which is the safe default.

                                     It applies only when mode is transport.";
                        ze:help
                            "Delete the SA when the peer declines transport mode.";
                    }

                    leaf df-bit {
                        type enumeration {
                            enum copy {
                                ze:help "Copy the DF bit of each inner IPv4 header into the tunnel header.";
                            }
                            enum clear {
                                ze:help "Write a clear DF bit, so routers on the path may fragment the tunnel packet.";
                            }
                            enum set {
                                ze:help "Write a set DF bit whatever the inner header carries.";
                            }
                        }
                        default copy;
                        description "What this peer's tunnel-mode Child SAs write into the DF bit of the
                                     outer IPv4 header they build.

                                     RFC 4301 Section 8.1: 'This means that it MUST be possible to
                                     configure the implementation's treatment of the DF bit (set,
                                     clear, copy from inner header) for each SA.  This applies to SAs
                                     where both inner and outer headers are IPv4.' The default copy
                                     is the option the same section makes mandatory.

                                     Clear lets a router on the path fragment a tunnel packet that
                                     exceeds its link, at the cost of reassembly at the far end. With
                                     copy, a router returns Fragmentation Needed for a DF-set packet
                                     and the tunnel's path MTU is learned and aged; with clear no path
                                     MTU is learned from the tunnel's packets, and the tunnel's MTU is
                                     its outer route's. Commit
                                     refuses clear or set on a transport-mode peer, which builds no
                                     outer header, and on a peer whose local-address or remote-address
                                     is IPv6, whose header has no DF bit. Commit refuses set on every
                                     dataplane today: the Linux kernel copies or clears the bit and has
                                     no flag that sets it, and VPP's ESP encrypt path ignores its set
                                     flag. A change restarts the peer.";
                        ze:help
                            "DF bit of the tunnel header: copy, clear or set.";
                    }

                    leaf dscp-map {
                        type union {
                            type enumeration {
                                enum copy {
                                    ze:help "Copy the DSCP of each inner header into the tunnel header.";
                                }
                            }
                            type uint8 {
                                range "0..63";
                            }
                        }
                        default copy;
                        description "The DSCP this peer's tunnel-mode Child SAs write into the outer
                                     header they build: copy, or one value 0 to 63 for every packet.

                                     RFC 4301 Section 5.1.2.1 constructs the outer DS Field as 'copied
                                     from inner hdr (5)', and note 5 says: 'If the packet will
                                     immediately enter a domain for which the DSCP value in the outer
                                     header is not appropriate, that value MUST be mapped to an
                                     appropriate value for the domain'. A value here is that mapping
                                     for a domain that gives all of this tunnel's traffic one class.

                                     The Linux kernel can copy or write 0 and nothing else, so on the
                                     Linux dataplane commit refuses a value from 1 to 63, and so does
                                     the Child SA install; VPP writes any value. Commit refuses a value on a
                                     transport-mode peer, which builds no outer header. A change
                                     restarts the peer.";
                        ze:help
                            "DSCP of the tunnel header: copy, or 0 to 63.";
                    }

                    leaf policy-priority {
                        type uint32 {
                            range "101..2147483647";
                        }
                        default 2000;
                        description "Where this peer's Security Policy Database entries sit in the
                                     operator's ordering of that database. A LOWER value is searched
                                     FIRST, in Ze and in the Linux kernel.

                                     RFC 4301 Section 4.4.1: 'The ordering requirement arises because
                                     entries often will overlap due to the presence of (non-trivial)
                                     ranges as values for selectors. Thus, a user or administrator MUST
                                     be able to order the entries to express a desired access control
                                     policy.' The same section binds this interface: it 'MUST support
                                     (total) ordering of these entries, as seen via this interface'.

                                     Two peers whose traffic selectors overlap, 0.0.0.0/0 on both for
                                     example, describe the same traffic. Give the one that must win the
                                     lower value. Nothing orders two peers that share a value, so
                                     when their tunnels overlap the one that establishes second is
                                     answered TS_UNACCEPTABLE and gets no Child SA: one packet could
                                     otherwise be sent into either tunnel, which RFC 3948 Section 5.1
                                     forbids. The default 2000 is the rank every peer took before
                                     this leaf existed.

                                     The range starts above 100, which is where the IKE control-plane
                                     bypass sits. A peer entry at or above that rank captures the IKE
                                     exchange that builds and rekeys the very SA it protects, and the
                                     tunnel could then never renegotiate. It ends at 2147483647, the
                                     largest rank Ze can carry to a dataplane.";
                        ze:help
                            "Rank of this peer's Security Policy Database entries, lowest searched first.";
                    }

                    leaf icmp-error-check {
                        type boolean;
                        default true;
                        description "Whether this peer's Child SAs carry the ICMP error processing of
                                     RFC 4301 Section 6.2.

                                     When true, an ICMP error that arrives on a Child SA with IP and
                                     ICMP headers this peer's traffic selectors do not cover is checked
                                     against the header of the packet that triggered it, with source and
                                     destination addresses and ports reversed, and is dropped unless that
                                     header matches the selectors of the SA it arrived on. An outbound
                                     ICMP error that no SA and no Security Policy Database entry would
                                     carry is sent through the Child SA that carries the return traffic
                                     of the packet it reports.

                                     When false, neither happens: an ICMP error is carried only where a
                                     traffic selector or a Security Policy Database entry covers its own
                                     headers, and every other one is dropped unread. RFC 4301 Section 6.2
                                     names that as the way to carry ICMP errors without inspecting their
                                     payload: configure an entry that explicitly carries them.

                                     The Linux XFRM dataplane performs both for an ICMP error addressed
                                     to Ze itself and for one Ze generates. For a forwarded ICMP error
                                     the kernel reaches the payload check only when no forward policy
                                     matches the error's own headers, and Ze's catch-all entry always
                                     does: a forwarded error that arrives on a Child SA with headers the
                                     selectors do not cover is dropped, whatever this leaf says. A
                                     forwarded error leaving towards a Child SA is mapped to the return
                                     SA only when the outbound lookup passes it untransformed: under
                                     `unmatched bypass` the catch-all lets it through and the kernel then
                                     maps it, while under `unmatched discard` the catch-all drops it
                                     first. Linux cannot tell a bypass entry from no entry here: an
                                     error that a vpn ipsec policy bypass entry, or the catch-all under
                                     `unmatched bypass`, would carry in clear is still mapped to the
                                     return SA, although Section 6.2 maps it only 'if no SPD entry would
                                     allow carriage of this outbound ICMP error message'. And an ICMP
                                     message arriving on a Child SA that an inbound discard entry
                                     refuses is delivered whenever its embedded header matches the SA.
                                     So while this leaf is true, commit refuses `unmatched bypass`, a
                                     bypass entry that would carry an ICMP error to this peer's remote
                                     selectors, and an inbound discard entry matching ICMP in a family
                                     the selectors carry, naming this leaf false as one fix; a
                                     configuration the daemon starts with logs the conflict at start
                                     instead. A peer with vti bind is exempt from these refusals:
                                     its Child SA policies carry the xfrm interface's if_id, which
                                     neither kernel path compares with an operator entry. The VPP
                                     dataplane, reached only through the test override
                                     ze.test.ike.dataplane, performs neither, so commit refuses this
                                     leaf true there and names icmp-error-check false as the fix.";
                        ze:help
                            "Check the payload of an ICMP error a Child SA carries.";
                    }

                    list traffic-selector {
                        key "number";
                        description "The traffic this peer's Child SAs carry, and the policy RFC 7296
                                     Section 2.9 narrows a peer's proposal against.

                                     When no entry is present the peer accepts whatever the remote
                                     endpoint proposes, which is the behavior of every configuration
                                     written before this list existed. Adding an entry restricts the
                                     peer: a proposal Ze cannot narrow to a non-empty subset of these
                                     entries is answered with TS_UNACCEPTABLE.

                                     RFC 7296 Section 2.9 permits several selectors, so this is a list.";
                        ze:help
                            "The traffic this peer's Child SAs carry.";

                        leaf number {
                            type string {
                                length "1..16";
                                pattern '[0-9]+';
                            }
                            description "Ze proposes the entries in the order the configuration declares them,
                                and it does not sort them by this number. The number is the key of the
                                list, so commit refuses a peer that declares one number twice.";
                            ze:help "Selector identifier. Order is the order of proposal.";
                        }

                        container local {
                            description "The prefix under it is mandatory once a traffic-selector entry exists,
                                and commit refuses an entry that leaves it out. The port under it takes
                                any unless the protocol leaf names a protocol that carries ports.";
                            ze:help "The local side of the selector pair (TSi when Ze
                                initiates, TSr when Ze responds).";

                            leaf prefix {
                                type zt:ip-prefix;
                                mandatory true;
                                description "The value is a CIDR prefix, and Ze installs it as the local selector
                                    of the kernel policy. Under mode transport the prefix MUST cover
                                    exactly one address, a /32 or a /128. RFC 7296 Section 2.23.1
                                    requires one IP address in TSi and in TSr, so commit refuses
                                    anything wider there.";
                                ze:help "Local traffic the Child SA carries.";
                            }

                            leaf port {
                                type union {
                                    type uint16 { range "1..65535"; }
                                    type enumeration {
                                        enum any {
                                            ze:help "Every port. RFC 7296 Section 3.13.1
                                                encodes it as start 0, end 65535.";
                                        }
                                    }
                                }
                                default any;
                                description "Local port of the selector.

                                             RFC 7296 Section 3.13.1 requires the port fields to be 0 and
                                             65535 whenever the protocol is 0 or defines no port, so a
                                             value other than any needs the protocol leaf to name a
                                             protocol that has ports. Linux accepts specific TCP, UDP,
                                             SCTP and UDP-Lite ports. A DCCP-specific port is refused
                                             because XFRM cannot select it. For ICMP the number is
                                             type times 256 plus code; for Mobility Header protocol
                                             135 it is Type times 256, with a zero low octet, so MH
                                             Type 5 has wire value 1280. Ze refuses every specific MH
                                             Type because the Linux receive-flow decoder does not
                                             extract it for exact classification; port any remains
                                             usable. VPP also refuses constrained MH and UDP-Lite
                                             selectors because its SPD ignores those fields.";
                                ze:help
                                    "Local port of the selector.";
                            }
                        }

                        container remote {
                            description "It obeys the rules the local container states. Ze narrows the peer's
                                proposal against the pair of prefixes, and it answers TS_UNACCEPTABLE
                                when no non-empty subset remains.";
                            ze:help "The remote side of the selector pair (TSr when Ze
                                initiates, TSi when Ze responds).";

                            leaf prefix {
                                type zt:ip-prefix;
                                mandatory true;
                                description "The value is a CIDR prefix, and Ze installs it as the remote
                                    selector of the kernel policy. The single-address rule the local
                                    prefix states applies here as well under mode transport.";
                                ze:help "Remote traffic the Child SA carries.";
                            }

                            leaf port {
                                type union {
                                    type uint16 { range "1..65535"; }
                                    type enumeration {
                                        enum any {
                                            ze:help "Every port. RFC 7296 Section 3.13.1
                                                encodes it as start 0, end 65535.";
                                        }
                                    }
                                }
                                default any;
                                description "It follows the same rule as the local port: a value other
                                             than any needs the protocol leaf. The ICMP type/code,
                                             MH high-octet Type encoding and backend limits stated
                                             on the local port apply here too.";
                                ze:help
                                    "Remote port of the selector.";
                            }
                        }

                        leaf protocol {
                            type uint8;
                            default 0;
                            description "IP protocol number the selector matches, such as 6 for TCP and
                                         17 for UDP. Zero matches every protocol, which is RFC 7296
                                         Section 3.13.1's 'protocol 0'.";
                            ze:help
                                "IP protocol number the selector matches.";
                        }
                    }

                    container authentication {
                        description "The mode leaf decides which leaf below it Ze reads. A pre-shared-secret peer
                            and an EAP password mode read pre-shared-secret. X.509 and every EAP mode
                            read certificate and ca-certificate, and commit refuses a peer that leaves
                            either of those empty.";
                        ze:help "Peer authentication settings.";

                        leaf mode {
                            type enumeration {
                                enum pre-shared-secret {
                                    ze:help "Both ends prove the same secret, taken from the pre-shared-secret leaf.";
                                }
                                enum x509 {
                                    ze:help "Sign AUTH with the named certificate and validate the remote one against ca-certificate.";
                                }
                                enum eap-tls {
                                    ze:help "EAP-TLS, Type 13 (RFC 5216): this peer authenticates with a certificate.";
                                }
                                enum eap-mschapv2 {
                                    ze:help "EAP-MSCHAPv2: this peer proves its password by challenge and response.";
                                }
                                enum eap-md5 {
                                    ze:help "EAP MD5-Challenge, Type 4 (RFC 3748 Section 5.4).";
                                }
                            }
                            mandatory true;
                            description "eap-md5 establishes no shared key, and RFC 7296
                                Section 2.16 discourages such a method: EAP methods that
                                do not establish a shared key SHOULD NOT be used, as
                                they are subject to a number of man-in-the-middle
                                attacks. The IKEv2 AUTH payloads are then keyed by SK_pi
                                and SK_pr instead of by an EAP MSK. The method
                                authenticates this peer to the far end and tells this
                                peer nothing about the far end. The daemon writes one
                                warning when this mode is adopted. Use eap-tls or
                                eap-mschapv2 unless the far end runs no other method.";
                            ze:help "Authentication mode.";
                        }

                        leaf pre-shared-secret {
                            type string;
                            ze:sensitive;
                            description "Ze reads the leaf when the mode is pre-shared-secret, and when the mode
                                is an EAP method that carries a password. The $9$ wrapper is removed
                                first, and the pre-shared-secret-encoding leaf then decides whether the
                                result is ASCII text or hexadecimal digit pairs.";
                            ze:help "Pre-shared key ($9$-encoded).";
                        }

                        leaf pre-shared-secret-encoding {
                            type enumeration {
                                enum ascii {
                                    ze:help "Read the secret as ASCII text, one octet for each character.";
                                }
                                enum hex {
                                    ze:help "Read the secret as hexadecimal digit pairs, two digits for each octet.";
                                }
                            }
                            default ascii;
                            description "RFC 7296
                                         Section 2.15 requires the management interface to
                                         accept both an ASCII string and a hex encoding of
                                         the shared secret. Set this to hex to supply the
                                         secret as hexadecimal digit pairs, which is the way
                                         to configure a secret holding non-printable octets.

                                         The encoding is stated here and is never guessed from
                                         the value. A secret such as abcdef0123456789 is both
                                         valid ASCII and valid hex, so reading it as hex would
                                         silently change an existing secret. A hex value with
                                         an odd length or a non-hexadecimal character is
                                         refused at commit rather than read as ASCII.";
                            ze:help
                                "How to read the pre-shared-secret value.";
                        }

                        leaf local-id {
                            type string;
                            description "Ze derives the ID type it sends from the shape of the value. An IP
                                address literal goes out as ID_IPV4_ADDR or ID_IPV6_ADDR, and every
                                other value as ID_FQDN. There is no ID_DER_ASN1_DN form, so commit
                                refuses a distinguished name. Commit also refuses a subtree or an
                                address range, because this leaf names the one identity Ze asserts. An
                                empty leaf sends the peer name.";
                            ze:help "Local identity for IKE negotiation.";
                        }

                        leaf remote-id {
                            type string;
                            description "When it is set,
                                Ze refuses an IKE_AUTH whose ID payload names another identity.
                                Comparable types are ID_IPV4_ADDR, ID_IPV6_ADDR, ID_FQDN,
                                ID_RFC822_ADDR, ID_KEY_ID, and ID_DER_ASN1_DN, and an address value
                                accepts the two address types alone. A distinguished name is
                                compared in RFC 4514 string form, and it binds against the
                                certificate subject exactly, octet for octet.

                                A value can name ONE peer or a SET of peers. RFC 4301 Section
                                4.4.3.1 requires both forms of Peer Authorization Database entry.
                                A set is written with the hierarchy separator in front, and it
                                admits the identities BELOW it and not the value itself:
                                '.example.com' admits vpn.example.com, '@example.com' admits
                                gateway@example.com, and ',ST=MA,C=US' admits every distinguished
                                name whose top relative distinguished names are ST=MA,C=US. An
                                address entry takes the same CIDR prefix the traffic-selector
                                leaves take, so '10.0.0.0/24' admits every address in that block.
                                ID_KEY_ID is always compared exactly, because an opaque octet
                                string has no hierarchy to cut.

                                The certificate binding stays per peer whichever form is used. A
                                peer admitted by a set must still assert an identity its own
                                certificate carries, so a set never widens what one certificate
                                proves.

                                When it is empty Ze checks no identity, so every certificate the
                                ca-certificate issued authenticates as this peer. Set it whenever
                                that authority issues to more than one client.";
                            ze:help "Identity the remote endpoint must assert.";
                        }

                        leaf remote-id-type {
                            type enumeration {
                                enum ipv4-address {
                                    ze:help "ID_IPV4_ADDR, an IPv4 address in four octets.";
                                }
                                enum ipv6-address {
                                    ze:help "ID_IPV6_ADDR, an IPv6 address in sixteen octets.";
                                }
                                enum fqdn {
                                    ze:help "ID_FQDN, a fully qualified domain name.";
                                }
                                enum rfc822-address {
                                    ze:help "ID_RFC822_ADDR, a mail address such as user@example.com.";
                                }
                                enum key-id {
                                    ze:help "ID_KEY_ID, an opaque octet string no certificate field can bind.";
                                }
                                enum der-asn1-dn {
                                    ze:help "ID_DER_ASN1_DN, the DER-encoded subject name of a certificate.";
                                }
                            }
                            description "The one IKE ID type the remote endpoint CAN assert, and when
                                         absent any type Ze CAN compare, which is the historical behavior.
                                         When it is set Ze refuses every other type, so a peer asserting
                                         ID_FQDN with the text of a configured mail address is refused.

                                         RFC 7296 Section 4 requires that it be possible to configure Ze to
                                         accept a PKIX certificate where the identity passed is ID_KEY_ID.
                                         An opaque key id corresponds to no certificate field, so Ze cannot
                                         derive that binding and refuses it by default. Setting this leaf to
                                         key-id is the operator stating that a chain to ca-certificate plus
                                         the exact key id IS the intended binding.

                                         It governs what Ze ACCEPTS, and the type Ze sends still follows
                                         the shape of local-id.";
                            ze:help
                                "The one IKE ID type the remote endpoint CAN assert.";
                        }

                        leaf session-resumption {
                            type boolean;
                            default true;
                            description "RFC 9190 Section 2.1.3 leaves resumption to each end: 'It is up
                                         to the EAP-TLS peer to use resumption', and 'the EAP-TLS server
                                         MAY choose to require a full handshake'. This leaf is that
                                         choice, and it covers both roles of this peer.

                                         With it true, an authentication that follows an earlier one
                                         skips the certificate exchange and reuses the session the ticket
                                         carries. Ze still checks the cached chain against the current
                                         ca-certificate and crl before it accepts the session, on both
                                         roles, so a revoked or expired certificate is refused on a
                                         resumed authentication as it is on a full one.

                                         With it false every authentication runs a full handshake. Ze
                                         still SENDS a session ticket, because RFC 9190 Section 2.1.2
                                         makes that a MUST with no condition on it; the ticket is simply
                                         never accepted back.

                                         Changing this leaf, the certificate, the ca-certificate or the
                                         crl discards every ticket ze holds for this peer.";
                            ze:help
                                "Let an EAP-TLS exchange with this peer resume an earlier one.";
                        }

                        leaf certificate-status-request {
                            type boolean;
                            default false;
                            description "RFC 9190 Section 5.4 recommends OCSP stapling for checking an
                                         EAP-TLS server's certificate chain, and puts a MUST on the peer
                                         that uses it: 'it MUST treat a CertificateEntry (but not the trust
                                         anchor) without a valid CertificateStatus extension as invalid and
                                         abort the handshake with an appropriate alert'. This leaf is what
                                         makes Ze such a peer.

                                         With it true, Ze refuses an authenticator that staples nothing,
                                         staples a response about another certificate, staples an expired
                                         one, or staples one that reports the certificate revoked or
                                         unknown. It also refuses a chain carrying an intermediate below
                                         the trust anchor, because Ze reads a stapled status for the leaf
                                         certificate alone and Section 5.4 makes an entry whose status it
                                         cannot read invalid.

                                         With it false, which is the default, Ze checks the same chain
                                         against the crl of the ca it validates against. Section 5.4
                                         requires that check on TLS 1.3 either way.

                                         It governs the peer role. As the authenticator Ze answers a
                                         Certificate Status Request whenever the pki certificate it
                                         presents carries an ocsp-response, whatever this leaf says.";
                            ze:help
                                "Check this peer's EAP-TLS certificate chain by the OCSP response it staples.";
                        }

                        leaf certificate-count {
                            type uint8 { range "1..4"; }
                            default 4;
                            description "The most X.509 certificates Ze sends for this peer, and the most it
                                         accepts from it. RFC 7296 Section 3.6 requires an implementation be
                                         capable of being configured to send and accept up to four. The
                                         default is that figure, so an operator who never sets this leaf
                                         gets the conformant behavior.

                                         A peer that sends more than this is REFUSED, never truncated. A
                                         silent trim would pass a count check and hide from the operator
                                         that the limit was reached. It would also make which certificates
                                         survive depend on the order the peer chose.";
                            ze:help
                                "The most X.509 certificates Ze sends to this peer and accepts from it.";
                        }

                        leaf hash-and-url {
                            type boolean;
                            default false;
                            description "When it is true Ze sends its certificate as a SHA-1 hash plus
                                         certificate-url, advertises HTTP_CERT_LOOKUP_SUPPORTED, and
                                         resolves a peer's Hash and URL payload.

                                         It defaults to false, and that default is a security property.
                                         Resolving a peer's payload fetches a URL that peer chose, and Ze
                                         must do that before it CAN authenticate the peer. With this leaf
                                         false Ze advertises nothing, a conforming peer sends no such
                                         payload, a non-conforming one is dropped, and no fetch is reachable.

                                         The enabled fetch takes the http scheme only, a 64 KiB cap, a
                                         5 second timeout, no redirects, denied destinations, and SHA-1
                                         verification before any parser.";
                            ze:help
                                "Use the Hash and URL certificate encodings of RFC 7296 Section 3.6.";
                        }

                        leaf certificate-url {
                            type string;
                            description "The http URL at which this device's own certificate is published,
                                         sent beside the SHA-1 hash when hash-and-url is true. RFC 7296
                                         Section 3.6 requires support for the http scheme.";
                            ze:help
                                "The http URL at which this device publishes its own certificate.";
                        }

                        leaf-list certificate-url-allow {
                            type zt:ip-prefix;
                            description "Destinations a certificate URL received from this peer CAN resolve
                                         to, beyond the fetcher's defaults. The fetcher refuses loopback,
                                         private, link-local and multicast addresses, and the cloud metadata
                                         address. It refuses them because the daemon runs on a router and
                                         holds routes an internet host does not. Naming a prefix here
                                         permits it.";
                            ze:help
                                "Extra destinations a certificate URL from this peer CAN resolve to.";
                        }

                        leaf ca-certificate {
                            ze:reference "pki-ca";
                            type string;
                            description "Name of the CA certificate in the PKI store. Required for
                                every EAP mode and for X.509. It is the trust anchor the remote
                                certificate must chain to, through any intermediate certificates the
                                peer sends. Without it any self-signed certificate would
                                authenticate. The remote certificate must also carry the remote-id
                                identity in a subject alternative name. Ze reads the subject common
                                name only when the certificate has no such extension.";
                            ze:help "Name of the CA certificate in the PKI store.";
                        }

                        leaf-list intermediate-certificate {
                            ze:reference "pki-ca";
                            type string;
                            description "Names of intermediate CA certificates held as ca entries in the
                                PKI store. Read in eap-tls mode only. When ze is the EAP-TLS
                                authenticator, it adds these certificates to path validation of the
                                client's certificate chain, beside the intermediates the client sends.
                                A client that sends its certificate alone then still validates, as
                                RFC 5216 Section 5.3 asks of an authenticator that cannot fetch the
                                intermediates a path needs. The certificates complete a path and never
                                end one: ca-certificate stays the only trust anchor. Commit refuses a
                                name that is not a PKI ca entry, an entry that is not a CA certificate,
                                and the list on a peer whose mode is not eap-tls.";
                            ze:help "PKI CA certificates that complete an EAP-TLS client chain.";
                        }

                        leaf certificate {
                            ze:reference "pki-certificate";
                            type string;
                            description "Name of the device certificate in the PKI store. Required for
                                every EAP mode, because RFC 7296 Section 2.16 makes the responder sign
                                its AUTH with a public key. Also used by X.509 mode. Ze sends this
                                certificate first, then the intermediate certificate the PKI entry
                                carries.";
                            ze:help "Name of the device certificate in the PKI store.";
                        }

                        container x509 {
                            description "X.509 certificate references (deprecated, use
                                the direct leaves). Ze reads a leaf here only when the
                                direct leaf of the same name is empty. A name set here
                                therefore meets the same requirement the direct leaf
                                meets, and it is checked against the PKI store the same
                                way.";
                            ze:help "X.509 certificate references, deprecated in favor of the direct leaves.";

                            leaf ca-certificate {
                                ze:reference "pki-ca";
                                type string;
                                description "Ze reads it only when the direct ca-certificate
                                    leaf is empty. It then satisfies the trust anchor that
                                    every EAP mode and X.509 require.";
                                ze:help "Name of the CA certificate in the PKI store.";
                            }

                            leaf certificate {
                                ze:reference "pki-certificate";
                                type string;
                                description "Ze reads it only when the direct certificate
                                    leaf is empty. It then satisfies the certificate that
                                    every EAP mode and X.509 require.";
                                ze:help "Name of the device certificate in the PKI store.";

                            }
                        }

                        container second-round {
                            description "A second authentication round in each direction, after the round the leaves
                                above configure (RFC 4739). Ze announces MULTIPLE_AUTH_SUPPORTED to this peer only
                                when local or remote below holds a round, and runs each round in its own IKE_AUTH
                                exchange, signing over the identity of that round. The tunnel establishes only
                                when every configured round succeeded. A peer that starts a second round remote
                                does not configure is refused with AUTHENTICATION_FAILED, and so is a peer that
                                finishes without the round remote configures. When the peer does not announce
                                MULTIPLE_AUTH_SUPPORTED, Ze completes with the first round alone and logs a
                                warning that the local round was skipped. Commit refuses a second round on a peer
                                whose mode is an EAP method. RFC 4739 Section 5: when the initiator authenticates
                                more than once, the responder reveals its identity before all of the initiator's
                                rounds have completed.";
                            ze:help "A second authentication round in each direction (RFC 4739).";

                            container local {
                                presence "Ze authenticates itself a second time to this peer.";
                                description "The credential Ze proves in its second round, with the identity it
                                    asserts for that round. Commit refuses mode x509 with no certificate and mode
                                    pre-shared-secret with no pre-shared-secret.";
                                ze:help "The credential Ze proves to this peer in its second round.";

                                leaf mode {
                                    type enumeration {
                                        enum pre-shared-secret {
                                            ze:help "Prove the secret taken from the pre-shared-secret leaf of this round.";
                                        }
                                        enum x509 {
                                            ze:help "Sign AUTH with the certificate named in this round.";
                                        }
                                    }
                                    mandatory true;
                                    description "Ze reads pre-shared-secret for mode pre-shared-secret and certificate for
                                        mode x509. An EAP method cannot run in a second round.";
                                    ze:help "How Ze authenticates in its second round.";
                                }

                                leaf pre-shared-secret {
                                    type string;
                                    ze:sensitive;
                                    description "Ze reads the leaf when the mode of this round is pre-shared-secret. The $9$
                                        wrapper is removed first, and pre-shared-secret-encoding then decides whether the
                                        result is ASCII text or hexadecimal digit pairs.";
                                    ze:help "Pre-shared key of the second round ($9$-encoded).";
                                }

                                leaf pre-shared-secret-encoding {
                                    type enumeration {
                                        enum ascii {
                                            ze:help "Read the secret as ASCII text, one octet for each character.";
                                        }
                                        enum hex {
                                            ze:help "Read the secret as hexadecimal digit pairs, two digits for each octet.";
                                        }
                                    }
                                    default ascii;
                                    description "The encoding is stated here and never guessed from the value, as for the
                                        first round. A hex value with an odd length or a non-hexadecimal character is
                                        refused at commit rather than read as ASCII.";
                                    ze:help "How to read the pre-shared-secret value of the second round.";
                                }

                                leaf id {
                                    type string;
                                    description "The identity Ze asserts in its second round, under the rules of local-id:
                                        an IP address literal goes out as ID_IPV4_ADDR or ID_IPV6_ADDR and every other
                                        value as ID_FQDN. Commit refuses a distinguished name, a subtree and an address
                                        range, and refuses the round when this leaf is not set: the round asserts an
                                        identity of its own, and a peer such as strongSwan selects the round's
                                        pre-shared key by that identity.";
                                    ze:help "Local identity asserted in the second round (required).";
                                }

                                leaf certificate {
                                    ze:reference "pki-certificate";
                                    type string;
                                    description "Name of the device certificate in the PKI store that signs the AUTH of
                                        this round. Required when the mode is x509. Ze sends this certificate first,
                                        then the intermediate certificate the PKI entry carries.";
                                    ze:help "Name of the second-round device certificate in the PKI store.";
                                }
                            }

                            container remote {
                                presence "Ze requires this peer to authenticate a second time.";
                                description "The credential the peer must prove in its second round, with the identity
                                    it must assert. Commit refuses mode x509 with no ca-certificate and mode
                                    pre-shared-secret with no pre-shared-secret.";
                                ze:help "The credential this peer must prove in its second round.";

                                leaf mode {
                                    type enumeration {
                                        enum pre-shared-secret {
                                            ze:help "The peer proves the secret taken from the pre-shared-secret leaf of this round.";
                                        }
                                        enum x509 {
                                            ze:help "The peer signs AUTH with a certificate that chains to ca-certificate.";
                                        }
                                    }
                                    mandatory true;
                                    description "Ze reads pre-shared-secret for mode pre-shared-secret and ca-certificate for
                                        mode x509. An EAP method cannot run in a second round.";
                                    ze:help "How the peer authenticates in its second round.";
                                }

                                leaf pre-shared-secret {
                                    type string;
                                    ze:sensitive;
                                    description "Ze reads the leaf when the mode of this round is pre-shared-secret. The $9$
                                        wrapper is removed first, and pre-shared-secret-encoding then decides whether the
                                        result is ASCII text or hexadecimal digit pairs.";
                                    ze:help "Pre-shared key the peer proves in the second round ($9$-encoded).";
                                }

                                leaf pre-shared-secret-encoding {
                                    type enumeration {
                                        enum ascii {
                                            ze:help "Read the secret as ASCII text, one octet for each character.";
                                        }
                                        enum hex {
                                            ze:help "Read the secret as hexadecimal digit pairs, two digits for each octet.";
                                        }
                                    }
                                    default ascii;
                                    description "The encoding is stated here and never guessed from the value, as for the
                                        first round. A hex value with an odd length or a non-hexadecimal character is
                                        refused at commit rather than read as ASCII.";
                                    ze:help "How to read the pre-shared-secret value of the second round.";
                                }

                                leaf id {
                                    type string;
                                    description "The identity the peer must assert in its second round, under the rules of
                                        remote-id: one identity, or a set written with the hierarchy separator in front,
                                        such as '.example.com' or an address prefix. When it is empty Ze checks no
                                        identity in this round.";
                                    ze:help "Identity the remote endpoint must assert in the second round.";
                                }

                                leaf id-type {
                                    type enumeration {
                                        enum ipv4-address {
                                            ze:help "ID_IPV4_ADDR, an IPv4 address in four octets.";
                                        }
                                        enum ipv6-address {
                                            ze:help "ID_IPV6_ADDR, an IPv6 address in sixteen octets.";
                                        }
                                        enum fqdn {
                                            ze:help "ID_FQDN, a fully qualified domain name.";
                                        }
                                        enum rfc822-address {
                                            ze:help "ID_RFC822_ADDR, a mail address such as user@example.com.";
                                        }
                                        enum key-id {
                                            ze:help "ID_KEY_ID, an opaque octet string no certificate field can bind.";
                                        }
                                        enum der-asn1-dn {
                                            ze:help "ID_DER_ASN1_DN, the DER-encoded subject name of a certificate.";
                                        }
                                    }
                                    description "The one IKE ID type the peer can assert in its second round, under the
                                        rules of remote-id-type. When it is absent any type Ze can compare is accepted.";
                                    ze:help "The one IKE ID type the peer can assert in the second round.";
                                }

                                leaf ca-certificate {
                                    ze:reference "pki-ca";
                                    type string;
                                    description "Name of the CA certificate in the PKI store that the peer's second-round
                                        certificate must chain to. Required when the mode is x509. The certificate must
                                        also carry the id of this round in a subject alternative name.";
                                    ze:help "Name of the second-round CA certificate in the PKI store.";
                                }
                            }
                        }
                    }

                    container vti {
                        description "The interface itself is declared under interfaces xfrm, where the if-id
                            leaf carries the identifier a bound security association must match. Ze reads
                            that if-id through the name under bind and installs this peer's Child SAs with it.";
                        ze:help "Virtual Tunnel Interface binding.";

                        leaf bind {
                            type string;
                            description "Route-based IPsec encrypts the traffic the routing table forwards
                                into the named XFRM interface. Commit refuses a name beside mode
                                transport, because an XFRM interface carries tunnel-mode encapsulation.
                                Ze installs the Child SA with the if-id of the named interface. A name
                                that is not an XFRM interface, or one whose if-id is 0, refuses the Child
                                SA, so the tunnel stays down rather than coming up unbound.";
                            ze:help "VTI interface name to bind this peer's traffic to.";
                        }
                    }
                }
            }
        }
    }
}
