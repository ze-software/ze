module ze-radius-conf {
    namespace "urn:ze:radius:conf";
    prefix radius;

    import ze-types { prefix zt; }
    import ze-extensions { prefix ze; }

    description "RADIUS admin-authentication configuration for Ze (RFC 2865)";

    revision 2026-09-04 {
        description "Add auth-method eap-md5 and eap-mschapv2: RADIUS/EAP admin login (RFC 3579)";
    }

    revision 2026-09-03 {
        description "Add auth-method: PAP or CHAP credential on the Access-Request";
    }

    revision 2026-07-08 {
        description "Initial revision: system/authentication/radius admin backend";
    }

    container system {
        description "The container holds the system-wide settings. This module attaches
                     the RADIUS operator authentication block under authentication.";
        // Several modules declare this container and the config tree merges
        // them, so this text states what THIS module attaches under it.
        ze:help
            "System-level settings";

        container authentication {
            description "System authentication settings. This module attaches the radius
                         block under it, which authenticates an operator login over SSH,
                         the web interface and MCP. The RADIUS backend joins the AAA
                         chain at priority 50, in front of TACACS+ at 100 and the local
                         accounts at 200. Ze builds it only where the server list holds
                         one entry or more, so a block with no server leaves the chain
                         unchanged.";
            ze:help
                "System authentication settings";

            container radius {
                description
                    "This block is separate from the L2TP subscriber RADIUS
                     path, which lives under the l2tp root.";
                ze:help
                    "RADIUS servers for operator login over SSH, web and MCP (RFC 2865).";

                list server {
                    key "address";
                    ordered-by user;
                    description "Ze sends the Access-Request to the first server, and it
                                 moves to the next one when that server does not answer.
                                 The order is the config order, because the list is
                                 ordered-by user. Each server gets a new Identifier, a new
                                 Request Authenticator, and the User-Password hidden again
                                 under the key of that server. RFC 2865 Section 4.1
                                 requires the new Request Authenticator: 'The Request
                                 Authenticator value MUST be changed each time a new
                                 Identifier is used.' Where every server fails, the AAA
                                 chain moves on to the local accounts, so an unreachable
                                 server never locks the operator out. A row that carries
                                 no key builds no RADIUS backend at all, rather than a
                                 shorter server list.";
                    ze:help
                        "RADIUS servers, tried in configured order";

                    leaf address {
                        type zt:ip-address;
                        description
                            "RADIUS operator authentication uses the shared udp4
                             client. An IPv6 literal does not resolve, and it
                             reads as unreachable.";
                        ze:help
                            "Server IPv4 address.";
                    }

                    leaf port {
                        type uint16 {
                            range "1..65535";
                        }
                        default 1812;
                        description "1812 is the port officially assigned to RADIUS.
                                     RFC 2865 Section 3 states that 'Exactly one RADIUS
                                     packet is encapsulated in the UDP Data field, where
                                     the UDP Destination Port field indicates 1812
                                     (decimal).' The range is 1 to 65535. Ze joins this
                                     port to the server address and resolves the pair as
                                     udp4. This block sends Access-Requests only, so it
                                     addresses the authentication port, and no
                                     accounting port is configured here.";
                        ze:help
                            "UDP authentication port (default 1812)";
                    }

                    leaf key {
                        type string {
                            length "1..max";
                        }
                        ze:sensitive;
                        description
                            "RFC 2865 Section 3 states that the secret MUST NOT
                             be empty (length 0). An empty secret lets an
                             attacker forge packets.";
                        ze:help
                            "RADIUS shared secret (RFC 2865).";
                    }

                    leaf require-message-authenticator {
                        type boolean;
                        default true;
                        description
                            "When true, Ze silently discards an Access-Accept,
                             Access-Reject, Access-Challenge or Protocol-Error
                             from this server that carries no
                             Message-Authenticator. This closes BlastRADIUS
                             (CVE-2024-3596), where an attacker forges an
                             Access-Accept from an Access-Reject.
                             draft-ietf-radext-deprecating-radius Section 4.1
                             asks for this per-server flag. Set it false only for
                             a server that predates 2024 and cannot sign its
                             answers. Ze signs every Access-Request whatever this
                             leaf says.";
                        ze:help
                            "Discard answers without Message-Authenticator (default true)";
                    }
                }

                leaf timeout {
                    type uint16 {
                        range "1..60";
                    }
                    default 3;
                    description "The value bounds the wait for one answer from one
                                 server. Each wait after a miss doubles the one before
                                 it. The default 3 therefore waits 3 seconds, then 6,
                                 then 12, across the three transmissions the default
                                 retries allows. The range is 1 to 60 seconds. The time
                                 one login spends on RADIUS is capped at 2 minutes,
                                 whatever timeout and retries hold. The login then falls
                                 through to the local accounts.";
                    ze:help
                        "Per-server request timeout in seconds";
                }

                leaf retries {
                    type uint8 {
                        range "0..10";
                    }
                    default 3;
                    description "The value counts the transmissions Ze sends to one
                                 server, and not the retransmissions after the first.
                                 With the default 3, Ze sends the Access-Request and
                                 retransmits it twice before it moves to the next
                                 server. The range is 0 to 10, and a configured 0 reaches
                                 the client as 3, because the client reads 0 as unset.
                                 The budget that bounds one login can then cancel the
                                 exchange partway through those transmissions. The login
                                 falls through to the local accounts, which is the answer
                                 a slow server gets too. Read timeout for the wait
                                 between the transmissions.";
                    ze:help
                        "Transmit attempts per server before failover";
                }

                leaf source-address {
                    type zt:ip-address;
                    description "Ze binds the outbound udp4 socket to this address, so
                                 every Access-Request leaves with it as the source. An
                                 IPv4 address here is also sent as NAS-IP-Address
                                 (RFC 2865 Section 4.1). Where the leaf is absent, the
                                 kernel picks the address of the outgoing interface and
                                 no NAS-IP-Address is sent. NAS-Identifier carries the
                                 hostname of this device either way, so the request
                                 meets Section 4.1 with the leaf unset. An address this
                                 host does not hold refuses the bind, and Ze logs the
                                 failure. The RADIUS backend then contributes nothing,
                                 and login falls through to the local accounts.";
                    ze:help
                        "Source IP for outbound RADIUS requests";
                }

                leaf auth-method {
                    type enumeration {
                        enum pap {
                            description
                                "Send the password in a User-Password attribute, hidden with the shared secret (RFC 2865 Section 5.2).";
                            ze:help "Send the password in a User-Password attribute, hidden with the shared secret.";
                        }
                        enum chap {
                            description
                                "Send MD5(identifier, password, challenge) in a CHAP-Password attribute, with the challenge in CHAP-Challenge (RFC 2865 Sections 5.3 and 5.40).";
                            ze:help "Send a CHAP-Password digest with the challenge in CHAP-Challenge.";
                        }
                        enum eap-md5 {
                            description
                                "Run an EAP conversation with MD5-Challenge inside EAP-Message attributes (RFC 3579 Section 3.1, RFC 3748 Section 5.4).";
                            ze:help "Run an EAP MD5-Challenge conversation inside EAP-Message attributes.";
                        }
                        enum eap-mschapv2 {
                            description
                                "Run an EAP conversation with MS-CHAPv2 inside EAP-Message attributes (RFC 3579 Section 3.1, RFC 2759).";
                            ze:help "Run an EAP MS-CHAPv2 conversation inside EAP-Message attributes.";
                        }
                    }
                    default "pap";
                    description
                        "RFC 2865 Section 4.1 and RFC 3579 Section 3.3 Note 1
                         permit one credential and never two, so ze sends
                         exactly one. Select chap only when the RADIUS server
                         holds the operator password in cleartext. RFC 2865
                         Section 2.2 states that 'CHAP requires that the user's
                         password be available in cleartext to the server so
                         that it can encrypt the CHAP challenge and compare that
                         to the CHAP response. If the password is not available
                         in cleartext to the RADIUS server then the server MUST
                         send an Access-Reject to the client.' A server that
                         stores password hashes cannot verify CHAP and rejects
                         every login. With pap the password is recoverable from
                         a captured request by anyone who holds the shared
                         secret, because Section 5.2 hides it with a reversible
                         XOR.
                         The two eap values run a full RADIUS/EAP conversation:
                         ze answers EAP itself, as the peer, with the password
                         the operator typed, and the server drives it through
                         Access-Challenge packets. eap-md5 carries the same
                         cleartext-password requirement as chap. eap-mschapv2
                         needs the server to hold the NT hash instead, which is
                         what an Active Directory backed server holds.";
                    ze:help
                        "Credential the Access-Request carries for an operator login.";
                }

                leaf profile-attribute {
                    type enumeration {
                        enum filter-id {
                            ze:help "RADIUS Filter-Id (11), RFC 2865 Section 5.11";
                        }
                    }
                    default "filter-id";
                    description
                        "Filter-Id is the only value. RFC 2865 Section 5.25 says
                         of Class that 'the client MUST NOT interpret the
                         attribute locally', so ze cannot read a profile name
                         out of Class.";
                    ze:help
                        "Access-Accept reply attribute that names the user's ze authorization profiles.";
                }

                leaf-list default-profile {
                    type string;
                    description
                        "This leaf is optional. Leave it unset when the RADIUS
                         server always names a profile through
                         profile-attribute. When the server does not name one,
                         and no default is set here, the login names no profile
                         and is denied. Ze never authorizes a user it cannot
                         attach a profile to.";
                    ze:help
                        "Ze authorization profiles used when the Access-Accept carries no profile-attribute.";
                }
            }
        }
    }
}
