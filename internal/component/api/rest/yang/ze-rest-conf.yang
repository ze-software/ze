module ze-rest-conf {
    namespace "urn:ze:api:rest:conf";
    prefix apirest;

    import ze-types { prefix zt; }
    import ze-extensions { prefix ze; }

    description "REST/HTTP API transport configuration. Compile-out-able via the
                 ze_rest build tag: this module contributes the rest{} container
                 into environment/api-server (Ze merges same-named containers
                 across modules). When ze_rest is off this schema is not
                 registered, so a rest{} config block is rejected as unknown.";

    revision 2026-06-26 {
        description "Split from ze-api-conf for per-encoding compile-out.";
    }

    container environment {
        description "Ze merges same-named containers across modules, so this container is one
                     tree that every service module writes into. ze-rest-conf contributes the
                     rest container alone.";
        ze:help "Environment settings (shared parent; merged across modules)";

        container api-server {
            description "The token that ze-api-conf declares beside this container is shared by
                         REST and gRPC, so an operator writes the bearer token once for both
                         transports.";
            ze:help "API engine settings (shared parent; merged across modules)";

            container rest {
                description "A plain HTTP listener is restricted to loopback. To reach the API from another host, put a TLS
                    terminator in front of the listener.";
                ze:help "REST and HTTP transport for the API server.";

                leaf enabled {
                    type boolean;
                    default false;
                    description "The default is false, so config starts no REST listener until
                                 the leaf is true. The environment variable
                                 ze.api-server.rest.enabled starts the transport with no leaf
                                 written. Ze parses the addresses and the CORS origin even when
                                 the transport stays off.";
                    ze:help "Enable REST API server";
                }

                list server {
                    key "name";
                    ze:listener;
                    description "The ze:listener extension marks this list, so config validation
                                 collects each endpoint and refuses a second listener that binds
                                 the same protocol, port and address. An empty list still binds
                                 one endpoint, 0.0.0.0 port 8081, from the refine defaults under
                                 it.";
                    ze:help "REST API listen endpoints";

                    leaf name {
                        type string;
                        description "The name is the list key alone. Ze binds the ip and the
                                     port of each entry and reads no name, so the name only
                                     keeps two entries of the list apart.";
                        ze:help "Server instance name";
                    }

                    uses zt:listener {
                        refine ip {
                            default "0.0.0.0";
                        }
                        refine port {
                            default 8081;
                        }
                    }
                }

                leaf cors-origin {
                    type string;
                    description "Ze copies the value into the Access-Control-Allow-Origin header
                                 of each API answer, and validates nothing in it. An empty leaf sends no
                                 CORS header, and a preflight request then gets 204 with no
                                 header. A preflight answer permits GET, POST, PUT, DELETE and
                                 OPTIONS, permits the Authorization and Content-Type headers,
                                 and holds for 86400 seconds.";
                    ze:help "CORS allowed origin (empty disables CORS headers)";
                }
            }
        }
    }
}
