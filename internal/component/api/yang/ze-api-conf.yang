module ze-api-conf {
    namespace "urn:ze:api:conf";
    prefix api;

    import ze-extensions { prefix ze; }

    description "API engine base configuration for Ze (shared api-server parent).
                 The REST and gRPC transports are compile-out-able: their config
                 containers live in ze-rest-conf (ze_rest) and ze-grpc-conf
                 (ze_grpc), which contribute rest{}/grpc{} into this api-server
                 via Ze's same-named-container merge. With a transport compiled
                 out its container is unregistered, so its config block is
                 rejected as unknown.";

    revision 2026-06-26 {
        description "Split rest/grpc transports out for per-encoding compile-out
                     (ze_rest / ze_grpc).";
    }
    revision 2026-01-01 {
        description "Initial revision";
    }

    container environment {
        description "The api-server container under it is the shared parent of the REST and gRPC
                     transports. ze-rest-conf and ze-grpc-conf merge their rest and grpc
                     containers into it, so a transport compiled out leaves no container to
                     configure.";
        ze:help "Environment settings for API transports";

        container api-server {
            description "The token leaf here is shared by both transports. Each transport starts
                         only when its own enabled leaf is true, or when
                         ze.api-server.rest.enabled or ze.api-server.grpc.enabled starts it.
                         Ze parses the addresses, the CORS origin and the TLS pair even when
                         the transport stays off.";
            ze:help "API engine settings (shared parent for the REST/gRPC transports)";

            leaf token {
                type string;
                ze:sensitive;
                description "When the token is set, a client MUST send the header
                             'Authorization: Bearer <token>'. Leave the leaf empty to
                             allow unauthenticated access.";
                ze:help "Bearer token for API authentication.";
            }
        }
    }
}
