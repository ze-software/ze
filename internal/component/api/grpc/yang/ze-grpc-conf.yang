module ze-grpc-conf {
    namespace "urn:ze:api:grpc:conf";
    prefix apigrpc;

    import ze-types { prefix zt; }
    import ze-extensions { prefix ze; }

    description "gRPC API transport configuration. Compile-out-able via the
                 ze_grpc build tag: this module contributes the grpc{} container
                 into environment/api-server (Ze merges same-named containers
                 across modules). When ze_grpc is off this schema is not
                 registered, so a grpc{} config block is rejected as unknown.";

    revision 2026-06-26 {
        description "Split from ze-api-conf for per-encoding compile-out.";
    }

    container environment {
        description "Ze merges same-named containers across modules, so this container is one
                     tree that every service module writes into. ze-grpc-conf contributes the
                     grpc container alone.";
        ze:help "Environment settings (shared parent; merged across modules)";

        container api-server {
            description "The token that ze-api-conf declares beside this container is shared by
                         REST and gRPC, so an operator writes the bearer token once for both
                         transports.";
            ze:help "API engine settings (shared parent; merged across modules)";

            container grpc {
                description "A listen address that is not loopback must carry authentication and
                             TLS, and Ze refuses to start the server without them. Without TLS
                             the bearer token that gates each call crosses the network in clear.
                             Ze accepts TLS 1.2 as its lowest version.";
                ze:help "gRPC API transport. Authenticated non-loopback listeners
                         require tls-cert and tls-key.";

                leaf enabled {
                    type boolean;
                    default false;
                    description "The default is false, so config starts no gRPC listener until
                                 the leaf is true. The environment variable
                                 ze.api-server.grpc.enabled starts the transport with no leaf
                                 written. Ze parses the addresses and the TLS pair even when the
                                 transport stays off.";
                    ze:help "Enable gRPC API server";
                }

                list server {
                    key "name";
                    ze:listener;
                    description "The ze:listener extension marks this list, so config validation
                                 collects each endpoint and refuses a second listener that binds
                                 the same protocol, port and address. An empty list still binds
                                 one endpoint, 0.0.0.0 port 50051, from the refine defaults
                                 under it.";
                    ze:help "gRPC API listen endpoints";

                    leaf name {
                        type string;
                        description "The name is the list key alone. Ze binds the ip and the
                                     port of each entry and reads no name, so the name only
                                     keeps two entries of the list apart.";
                        ze:help "Server instance name";
                    }

                    uses zt:listener {
                        refine ip {
                            default "0.0.0.0";
                        }
                        refine port {
                            default 50051;
                        }
                    }
                }

                leaf tls-cert {
                    type string;
                    description "Write tls-cert and tls-key together. Ze refuses to start the
                                 server when one of the two is written and the other is not. Ze
                                 reads the pair from disk at start, so a path that names no file
                                 stops the server with an error.";
                    ze:help "Path to TLS certificate file for gRPC";
                }

                leaf tls-key {
                    type string;
                    ze:sensitive;
                    description "The leaf names the file that holds the private key of tls-cert,
                                 and Ze reads the two together at start. Ze marks the leaf
                                 ze:sensitive, so ze config dump prints the value $9$-encoded.";
                    ze:help "Path to TLS private key file for gRPC";
                }
            }
        }
    }
}
