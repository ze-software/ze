module ze-traffic-control-conf {
    namespace "urn:ze:traffic:conf";
    prefix tc;

    import ze-extensions { prefix ze; }

    description "Traffic subsystem configuration for Ze.
                 Owns the top-level `traffic` container. The `control`
                 subtree configures queueing disciplines, classes, and
                 filters per network interface. Sibling subtrees (e.g.
                 `usage`, contributed by the traffic-usage plugin) augment
                 the same `traffic` parent.";

    revision 2026-10-27 {
        description "Represent the classless tc TBF rate on the root qdisc.";
    }
    revision 2026-10-12 {
        description "Make qdisc a presence container, so its mandatory type is
                     required only when a qdisc is configured, not in every
                     interface entry (RFC 7950 Section 7.6.5).";
    }
    revision 2026-07-02 {
        description "Nest traffic-control under traffic/control; the container
                     now owns the shared traffic parent that traffic-usage
                     augments.";
    }
    revision 2026-04-13 {
        description "Initial revision";
    }

    typedef qdisc-type {
        type enumeration {
            enum htb { ze:help "The Hierarchical Token Bucket qdisc."; }
            enum hfsc { ze:help "The Hierarchical Fair Service Curve qdisc."; }
            enum fq { ze:help "The Fair Queue qdisc."; }
            enum fq_codel { ze:help "The Fair Queue Controlled Delay qdisc."; }
            enum sfq { ze:help "The Stochastic Fair Queue qdisc."; }
            enum tbf { ze:help "The Token Bucket Filter qdisc."; }
            enum netem { ze:help "The Network Emulator qdisc."; }
            enum prio { ze:help "The Priority qdisc."; }
        }
        description "Queueing discipline type. The clsact and ingress hooks are
                     not offered: they attach at the ingress hook rather than at
                     the root, they carry no classes, and the mirror and the
                     sampling paths own that hook already. Ze still names them
                     when it reads an interface that carries one.";
    }

    typedef rate-bps {
        type string {
            pattern '[0-9]+(mbit|kbit|gbit|bit|mbps|kbps|gbps|bps)';
        }
        description "Rate in bits or bytes per second (e.g., 10mbit, 100kbps)";
    }

    typedef filter-type {
        type enumeration {
            enum mark { ze:help "Match the packet mark, with the tc fw filter."; }
            enum dscp { ze:help "Match the DSCP value of the packet."; }
            enum protocol { ze:help "Match the protocol of the packet."; }
        }
        description "Traffic filter match type";
    }

    container traffic {
        description "Two subtrees sit under it, and they are independent. control programs the
queueing disciplines of each interface, which decides which packet leaves first. usage
counts bytes with an eBPF program, and it changes no packet. Each subtree comes from its
own plugin, so removing one plugin removes that subtree alone.";
        ze:help "Traffic subsystem: QoS control and byte-usage accounting.";

        container control {
            description "One entry exists for each interface Ze programs. The backend leaf
names the program that applies the entries.";
            ze:help "Traffic control configuration of each interface.";

            leaf backend {
                type string;
                default "tc";
                description "The default backend is tc, the queueing disciplines of Linux iproute2.
Another backend declares itself through traffic.RegisterBackend. The ze:backend YANG
extension on a feature node declares which backend supports that feature. The
commit-time gate reads that extension and rejects a config that names a qdisc or a
filter type the backend does not support.";
                ze:help "Traffic control backend that programs the queueing disciplines.";
            }

            list interface {
                key "name";
                description "The list key is the interface name.";
                ze:help "Traffic control of one named interface.";

                leaf name {
                    type string;
                    description "The interface MUST exist in the interface configuration.";
                    ze:help "Name of the interface this entry controls.";
                }

                container qdisc {
                    presence "Attach a root queueing discipline to the interface.";
                    description "Ze attaches this qdisc at the root of the interface, and every
class hangs beneath it. An interface entry with no qdisc block attaches none.";
                    ze:help "The root queueing discipline of the interface.";

                    leaf type {
                        type qdisc-type;
                        mandatory true;
                        description "The commit-time gate rejects a type the configured backend
does not support.";
                        ze:help "Type of the queueing discipline.";
                    }

                    leaf rate {
                        when "../type = 'tbf'";
                        type rate-bps;
                        ze:backend "tc";
                        description "Root TBF rate. Required by backend tc for tbf, which
has no configurable classes. The backend refuses a rate it cannot represent
without truncation. VPP uses class policers instead and refuses this leaf.";
                        ze:help "Rate of the classless TBF root.";
                    }

                    leaf default-class {
                        type leafref {
                            path "../class/name";
                        }
                        description "The value is the name of a class in the class list of this
qdisc. The leafref refuses a name no class of this qdisc carries.";
                        ze:help "Name of the class that takes the unclassified traffic.";
                    }

                    list class {
                        key "name";
                        description "The list key is the class name. A class carries a rate, a
ceil, a priority, and the filters that select its traffic.";
                        ze:help "One traffic class of the queueing discipline.";

                        leaf name {
                            type string {
                                length "1..255";
                            }
                            description "The name is the list key, and the default-class leaf
of the qdisc names one of them.";
                            ze:help "Name of this class.";
                        }

                        leaf rate {
                            type rate-bps;
                            mandatory true;
                            description "The value is a number and a unit, for example 10mbit
or 100kbps.";
                            ze:help "Rate this class is guaranteed.";
                        }

                        leaf ceil {
                            type rate-bps;
                            description "An absent leaf takes the value of the rate leaf.";
                            ze:help "Largest rate this class can reach.";
                        }

                        leaf priority {
                            type uint8;
                            description "The value 0 is the highest priority.";
                            ze:help "Scheduling priority of this class.";
                        }

                        list match {
                            key "type";
                            description "The list key is the match type, so one class carries at
most one match of each type.";
                            ze:help "A filter that classifies a packet into this class.";

                            leaf type {
                                type filter-type;
                                description "The commit-time gate rejects a filter type the
configured backend does not support.";
                                ze:help "Type of the match.";
                            }

                            leaf value {
                                type string;
                                mandatory true;
                                description "A mark filter takes a hex value. A dscp filter
takes a DSCP name. A protocol filter takes a protocol name.";
                                ze:help "Value the filter matches.";
                            }
                        }
                    }
                }
            }
        }
    }
}
