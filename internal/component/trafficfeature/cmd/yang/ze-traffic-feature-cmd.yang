module ze-traffic-feature-cmd {
    namespace "urn:ze:traffic-feature:cmd";
    prefix trafficfeaturecmd;
    import ze-extensions { prefix ze; }
    // The command container-merges onto the shared `traffic` namespace.
    description "The show traffic feature command tree, owned by the trafficfeature component.";
    revision 2026-07-13 { description "Nest under show traffic feature (was traffic-feature), per R9 namespace split."; }
    revision 2026-07-02 { description "Initial: neutral per-source traffic feature signals CLI."; }

    container show {
        config false;
        ze:help "Read-only commands to inspect system, protocol, and network state.";

        container traffic {
            config false;
            // Repeat the canonical description owned by ze-traffic-cmd.yang
            // verbatim, because the command-tree merge keeps the first text.
            ze:help "Traffic subsystem: QoS control and byte-usage accounting.";

            container feature {
                config false;
                ze:command "ze-trafficfeature:show-traffic-feature";
                description "The signals are fan-out (distinct destinations), out/in
byte ratio (exfiltration), destination-port entropy, new-peer, rare-port/proto,
and coarse beaconing.
Without arguments, shows the top source entities. With 'name <address>',
filters to one source.";
                ze:help "Show neutral per-source traffic feature signals.";
                leaf name {
                    type string;
                    description "A source IP address, compared as text against each entry's
address. Only the entries with that exact address are listed.";
                    ze:help "Source address filter";
                }
            }
        }
    }
}
