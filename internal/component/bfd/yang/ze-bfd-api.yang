module ze-bfd-api {
    namespace "urn:ze:bfd:api";
    prefix bfdapi;

    import ze-extensions { prefix ze; }

    description
        "BFD API operations for Ze. RPCs for observing session state
         and resolved profiles. RFC 5880 sections 6.8.1 (state
         variables) and 6.8.4 (detection time) supply the field
         semantics.";

    revision 2026-04-11 {
        description "Initial BFD observability API (spec-bfd-4).";
    }

    rpc show-sessions {
        description "Each row carries the peer, the state and the diagnostic code. It also
carries the two discriminators, the transmit, receive and detection intervals, the packet
counters and the recent state changes. The command fails with bfd: plugin not loaded when
BFD is not running.";
        ze:help "Return every live BFD session.";
        output {
            leaf sessions {
                type string;
                description "One object per session, taken from a snapshot of the service at
the moment of the call. An empty array means BFD runs and holds no session.";
                ze:help "JSON array of session objects.";
            }
        }
    }

    rpc show-session {
        description "The peer must be an IP address, and a value that does not parse is refused
before the lookup. A peer with no session is reported as no session for that peer.";
        ze:help "Return one BFD session by peer address.";
        input {
            leaf peer {
                type string;
                mandatory true;
                description "The address in its usual text form, with no prefix length. It
is matched against the peer address of each session.";
                ze:help "Peer IPv4 or IPv6 address.";
            }
        }
        output {
            leaf session {
                type string;
                description "The same fields a show-sessions row carries, for the one session
the peer selected.";
                ze:help "JSON object with session detail.";
            }
        }
    }

    rpc show-profile {
        description "Without a name every profile is answered. Each one carries the detect
multiplier, the desired transmit interval and the required receive interval in microseconds,
and whether the profile is passive.";
        ze:help "Return resolved BFD profile parameters.";
        input {
            leaf name {
                type string;
                description "With a name, the answer is that one profile object rather than
an array. A name no profile carries fails with bfd: no profile named <name>.";
                ze:help "Profile name (empty returns every profile).";
            }
        }
        output {
            leaf profiles {
                type string;
                description "The values are the ones in effect after inheritance, not the
ones typed in the configuration.";
                ze:help "JSON array of profile objects.";
            }
        }
    }
}
