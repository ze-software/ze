module ze-bfd-cmd {
    namespace "urn:ze:bfd:cmd";
    prefix bfdcmd;
    import ze-extensions    { prefix ze; }
    import ze-cli-show-cmd  { prefix clishowcmd; }
    description
        "BFD session state, timers, and profile configuration.";
    revision 2026-04-11 {
        description "Initial revision (spec-bfd-4).";
    }

    augment "/clishowcmd:show" {
        container bfd {
            config false;
            description "The timers reported are the negotiated ones and not the configured ones.
                         BFD takes the slower of the two peers' intervals. A session can therefore
                         run slower than this router asked for.";
            ze:help "BFD session state and timer configuration.";

            container sessions {
                config false;
                ze:command "ze-bfd:show-sessions";
                ze:rpc "ze-bfd-api:show-sessions";
                description "One line per session: peer address, state, negotiated
tx/rx intervals, and detect multiplier.";
                ze:help "List all active BFD sessions.";
            }

            container session {
                config false;
                description "The address selects a single session. A router with several sessions to one peer
                             over different links reports each of them separately.";
                ze:help "Show one BFD session selected by peer address.";

                container address {
                    config false;
                    ze:command "ze-bfd:show-session";
                    ze:rpc "ze-bfd-api:show-session";
                    description "Pass the peer address. Returns local/remote
discriminators, negotiated timers, detection time, and packet counters.";
                    ze:help "Show full detail for one BFD session.";
                    leaf address {
                        type string;
                        mandatory true;
                        description "An IPv4 or IPv6 address in its usual text form. A value that
does not parse fails with bfd: invalid peer address before any lookup.";
                        ze:help "Peer address";
                    }
                }
            }

            container profile {
                config false;
                ze:command "ze-bfd:show-profile";
                ze:rpc "ze-bfd-api:show-profile";
                description "Returns min-tx, min-rx, and detect-multiplier after
inheritance. Use 'show bfd profile' for every profile or 'show bfd profile
name <name>' for one profile.";
                ze:help "Show BFD timer profiles with effective values.";

                container name {
                    config false;
                    ze:command "ze-bfd:show-profile";
                    ze:rpc "ze-bfd-api:show-profile";
                    description "Give the profile name after the name keyword. The answer is one profile object, not a list. An unknown name fails with 'bfd: no profile named <name>'.";
                    ze:help "Show one BFD profile by name.";
                    leaf name {
                        type string;
                        mandatory true;
                        description "The name a bfd profile block declares in the configuration.
The match is exact, and the values answered are the ones in effect after inheritance.";
                        ze:help "Profile name";
                    }
                }
            }
        }
    }
}
