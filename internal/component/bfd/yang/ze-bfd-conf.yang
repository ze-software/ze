module ze-bfd-conf {
    namespace "urn:ze:bfd:conf";
    prefix bfd;

    import ze-extensions { prefix ze; }

    description
        "Bidirectional Forwarding Detection (BFD) configuration for Ze.

         Implements RFC 5880 (base), RFC 5881 (single-hop), and
         RFC 5883 (multi-hop). Profiles hold reusable timer and feature
         bundles. Sessions explicitly pinned in configuration exist even
         without a protocol client; protocol-driven sessions (from BGP,
         OSPF, static routes) are created at runtime via the plugin
         Service interface and do not appear here.";

    revision 2026-10-18 {
        description "auth gains secret-hex, a hexadecimal form of the shared secret, in a choice with secret.";
    }

    revision 2026-09-20 {
        description "enabled false now stops a runtime session as well as a pinned one.";
    }

    revision 2026-04-11 {
        description "Initial BFD config skeleton.";
    }

    container bfd {
        description "The container holds the plugin switch, the reusable profiles, and the sessions an
            operator pins. A session that BGP or a static route asks for at runtime does not appear
            here. A protocol client reaches the plugin through its Service interface instead.";
        ze:help "BFD control configuration for Ze.";

        leaf enabled {
            type boolean;
            default true;
            description "The default is true. false stops every BFD session, the ones pinned in this bfd
                container and the ones a protocol client asks for at runtime. A reload to false stops the
                pinned sessions already running. A config that sets false while a BGP peer, a static
                next-hop or an OSPF interface still opts into BFD is refused, naming those clients, so
                remove the opt-ins first. To stop the session of one peer only, remove the bfd container
                from that peer or set its enabled leaf to false.";
            ze:help "Master switch for the BFD plugin.";
        }

        leaf persist-dir {
            type string;
            description "DEPRECATED, retained for back-compat and scheduled for removal. The value is no longer interpreted
                as a directory. TX sequence numbers for Meticulous Keyed authentication now persist to the shared
                managed store (the database/ tree), instead of a loose file. A non-empty value still opts a session
                into persistence. RFC 5880 Section 6.7.3 requires the sequence to survive process restarts. Without
                this leaf set, Meticulous sessions still work at runtime, but a fresh process loses its sequence
                floor until the peer's replay window slides forward.";
            ze:help "DEPRECATED. A non-empty value opts a session into sequence persistence.";
        }

        leaf bind-v6 {
            type boolean;
            default false;
            description "When this leaf is true, the BFD plugin also binds an IPv6 socket (::0) alongside the IPv4 socket for
                every (vrf, mode) loop. The paired sockets share the same RX channel through a transport.Dual
                wrapper, and send routes by destination address family. Stage 2b (spec-bfd-2b-ipv6-transport) ships
                this leaf. A pinned IPv6 session requires the leaf to be set explicitly, so an operator who does not
                need IPv6 does not open a second socket per loop.";
            ze:help "Bind an IPv6 socket beside the IPv4 socket on every loop.";
        }

        list profile {
            key "name";
            description "Reusable timer and feature profile. Sessions reference a profile by name and inherit every field
                below.";
            ze:help "Reusable timer and feature profile.";

            leaf name {
                type string;
                description "A session names this value in its own profile leaf. Ze refuses a session whose
                    profile leaf names no declared profile, so a typo stops the config load. A profile
                    no session names is parsed and changes nothing.";
                ze:help "Profile name used as the reference key.";
            }

            leaf detect-multiplier {
                type uint8 {
                    range "1..255";
                }
                default 3;
                description "Number of consecutive missed Control packets that trigger a Down transition. RFC 5880 Section 6.8.4.";
                ze:help "Consecutive missed Control packets that trigger a Down transition.";
            }

            leaf desired-min-tx-us {
                type uint32;
                default 300000;
                description "Local target transmit rate in microseconds. The slow-start floor of 1 000 000 us applies while the
                    session is not Up, per RFC 5880 Section 6.8.3.";
                ze:help "Local target transmit rate in microseconds.";
            }

            leaf required-min-rx-us {
                type uint32;
                default 300000;
                description
                    "Ze advertises the value as Required Min RX Interval, and a peer that obeys it
                    does not transmit faster. The detection time is the peer's Detect Multiplier times
                    the larger of this value and the peer's Desired Min TX Interval. While echo mode
                    runs, Ze raises the advertised value to 1000000 microseconds and starts a Poll
                    sequence, because the echo packets already prove the path.";
                ze:help "Minimum inter-packet gap the local end can handle,
                         in microseconds.";
            }

            leaf passive {
                type boolean;
                default false;
                description "Active, which is the default, transmits from session creation. Passive transmits nothing until a
                    Control packet arrives from the peer. RFC 5883 Section 4.3. A single-hop session, BGP peer or static
                    next-hop that uses a passive profile is refused: RFC 5881 Section 3 requires the Active role on a single hop.";
                ze:help "Wait for a peer Control packet before this session transmits.";
            }

            container echo {
                presence "enables BFD Echo mode on sessions using this profile";
                description "RFC 5880 Section 6.4 / RFC 5881 Section 5 Echo mode. Echo mode is single-hop only, because RFC 5883
                    Section 3 prohibits multi-hop echo: a multi-hop session or BGP peer that uses an echo profile is refused.
                    When echo is active, the engine sends echo packets on UDP port 3785 at the peer's advertised
                    RequiredMinEchoRxInterval. The engine then slows its async Control TX to the peer's
                    RequiredMinRxInterval.";
                ze:help "BFD Echo mode (RFC 5880 Section 6.4, RFC 5881 Section 5).";

                leaf desired-min-echo-tx-us {
                    type uint32;
                    default 50000;
                    description "Local target echo transmit rate in microseconds. The effective echo rate is max(local desired, peer
                        RequiredMinEchoRx).";
                    ze:help "Local target echo transmit rate in microseconds.";
                }
            }

            container auth {
                presence "enables authentication on sessions using this profile";
                description "RFC 5880 Section 6.7 authentication parameters. Sessions inheriting this profile sign every outgoing
                    Control packet with the configured type, and verify incoming packets with the same key. There is no
                    default type, and authentication runs only on the type the operator names here.";
                ze:help "Authentication parameters (RFC 5880 Section 6.7).";

                leaf type {
                    type enumeration {
                        enum simple-password {
                            ze:help "RFC 5880 Section 6.7.2 Simple Password, sent in clear in every Control packet.";
                        }
                        enum keyed-md5 {
                            ze:help "RFC 5880 Section 6.7.3 Keyed MD5.";
                        }
                        enum meticulous-keyed-md5 {
                            ze:help "RFC 5880 Section 6.7.3 Meticulous Keyed MD5 (strict sequence increase).";
                        }
                        enum keyed-sha1 {
                            ze:help "RFC 5880 Section 6.7.4 Keyed SHA1.";
                        }
                        enum meticulous-keyed-sha1 {
                            ze:help "RFC 5880 Section 6.7.4 Meticulous Keyed SHA1 (strict sequence increase).";
                        }
                    }
                    mandatory true;
                    description "Authentication type. There is no default. The operator names the type, and simple-password is never
                        selected on their behalf. simple-password is RFC 5880 Section 6.7.2 Simple Password. The password
                        travels in clear in every Control packet and the section never changes, so it protects against a
                        misconfigured peer and against nothing else. It does not protect against a listener on the path, who
                        reads the password from one packet, and it carries no Sequence Number, so a captured packet can be
                        replayed. Choose a keyed type wherever the path is not already trusted.";
                    ze:help "Authentication type, which the operator must name.";
                }

                leaf key-id {
                    type uint8;
                    mandatory true;
                    description "Ze writes the value into the authentication section of every Control packet
                        it sends. Ze discards a received packet that carries another value, which RFC 5880
                        Section 6.7.2 requires for Simple Password. Both ends must name the same key-id
                        and the same secret. The range is 0 to 255.";
                    ze:help "Auth Key ID (RFC 5880 Section 6.7.1).";
                }

                choice secret-form {
                    mandatory true;
                    description "Name the shared secret in exactly one form. secret takes an ASCII string and uses its
                        bytes as the key. secret-hex takes any binary string written in hexadecimal, so a key holding
                        a zero byte or a byte above 0x7F can be configured (RFC 5880 Sections 6.7.2, 6.7.3 and 6.7.4).
                        Ze refuses a profile that names both forms or neither.";
                    ze:help "The shared secret, as an ASCII string or in hexadecimal.";

                    leaf secret {
                        type string;
                        ze:sensitive;
                        description "Shared secret as an ASCII string, whose bytes are the key. Redacted from `ze config
                            show` output. The MD5 variants take a secret of up to 16 bytes (RFC 5880 Section 6.7.3) and
                            the SHA1 variants one of up to 20 bytes (Section 6.7.4). Both pad a shorter secret with
                            zeros, and a longer one is refused at parse time. The simple-password type carries the
                            secret itself on the wire, so it must be 1 to 16 bytes, and a longer one is refused at
                            parse time too (RFC 5880 Section 6.7.2).";
                        ze:help "Shared secret as an ASCII string, redacted from `ze config show` output.";
                    }

                    leaf secret-hex {
                        type string {
                            pattern "([0-9a-fA-F][0-9a-fA-F])+";
                            length "2..40";
                        }
                        ze:sensitive;
                        description "Shared secret as a binary string in hexadecimal, two digits for each byte with no
                            0x prefix, upper or lower case. Redacted from `ze config show` output. The decoded key
                            obeys the same limits as secret: 1 to 16 bytes for simple-password, up to 16 bytes for
                            the MD5 variants and up to 20 bytes for the SHA1 variants (RFC 5880 Sections 6.7.2,
                            6.7.3 and 6.7.4).";
                        ze:help "Shared secret as hexadecimal digits, two for each byte, redacted from output.";
                    }
                }
            }
        }

        list single-hop-session {
            key "peer vrf interface";
            description "Per-link BFD session (RFC 5881). Port 3784, TTL=255. A protocol client MUST NOT use this list. A
                protocol client calls the plugin Service interface at runtime.";
            ze:help "Per-link BFD session on port 3784 with TTL 255 (RFC 5881).";

            leaf peer {
                type string;
                description "The value is the first word after the list name, so single-hop-session
                    203.0.113.9 names this peer. Ze refuses an address it cannot parse, and IPv4 and IPv6
                    are both accepted. RFC 5881 Section 5 requires a received TTL of 255, so Ze discards
                    a Control packet from this peer that crossed a router. An IPv6 link-local peer
                    (fe80::/10) is refused unless the entry names its link in interface, and an address
                    written with a zone (fe80::b%eth0) is refused: the link is written in interface.";
                ze:help "Peer IPv4 or IPv6 address.";
            }
            leaf local {
                type string;
                description "While the leaf is absent, the kernel selects the source address. The address
                    is part of the session key. A change to it therefore releases the running session,
                    and creates a new one at the next config load. An address written with a zone is
                    refused: the link is written in interface.";
                ze:help "Local source address (optional).";
            }
            leaf interface {
                type string;
                description "Ze binds the socket of the loop to this interface with SO_BINDTODEVICE. One
                    socket serves every session of one VRF and hop mode. Ze binds it only when each
                    session in the default VRF names the same interface. A mix of names leaves the
                    socket unbound, with a warning in the log. In a VRF other than default the VRF
                    device wins, and this leaf is dropped from the socket binding; it still names the
                    session's link. An IPv6 link-local peer needs this leaf in every VRF.";
                ze:help "Egress interface name.";
            }
            leaf vrf {
                type string;
                default "default";
                description "A name other than default binds the socket to the VRF device of that name. The
                    interface leaf of every session in that VRF is then dropped, and Ze logs the names it
                    dropped once for each loop. An empty value is refused: the leaf is part of the key.";
                ze:help "Routing instance the session runs in. The default instance is named default.";
            }
            leaf profile {
                type leafref {
                    path "../../profile/name";
                    require-instance true;
                }
                description "Commit refuses a name that no profile declares, and names the profiles that
                    exist. Without this leaf the session takes
                    the engine values: a detect multiplier of 3, and 1000000 microseconds for both the
                    transmit target and the receive floor.";
                ze:help "Named profile to inherit timer parameters from.";
            }
            leaf shutdown {
                type boolean;
                default false;
                description
                    "The session keeps its configuration and its place in the list, and Ze holds it
                    in AdminDown. Ze applies the value again at each reload, so a change from true to
                    false brings the session back with no restart. Delete the list entry to remove the
                    session instead.";
                ze:help "When true, the session stays in AdminDown state.
                         RFC 5880 Section 6.8.16.";
            }
        }

        list multi-hop-session {
            key "peer local vrf";
            description
                "The 255-TTL test of a single-hop session cannot work over several hops. The
                min-ttl leaf is the cheap protection here, and authentication is the strong one. Ze
                refuses an entry whose profile enables echo. RFC 5883 Section 3 states that the Echo
                function MUST NOT be used over multiple hops. The local leaf is required here, and it
                is optional on a single-hop session.";
            ze:help "Multi-hop BFD session (RFC 5883). Port 4784, no GTSM.";

            leaf peer {
                type string;
                description "The value is the first word after the list name, so multi-hop-session
                    203.0.113.9 names this peer. Ze refuses an address it cannot parse, and IPv4 and
                    IPv6 are both accepted. The peer, the local address and the VRF together identify
                    the session.";
                ze:help "Address of the remote system this session runs to.";
            }
            leaf local {
                type string;
                description "Ze refuses an entry that omits this leaf. The address is the source of every
                    Control packet Ze sends, and it is part of the session key. RFC 5883 Section 4.1
                    states that two sessions between the same pair of systems must differ in at least
                    one endpoint address. The reason is that the first packet carries a Your
                    Discriminator of 0.";
                ze:help "Local source address. Required for multi-hop.";
            }
            leaf vrf {
                type string;
                default "default";
                description "A name other than default binds the socket to the VRF device of that name. Ze
                    runs one socket for each pair of VRF and hop mode, so every multi-hop session in one
                    VRF shares it. An empty value is refused: the leaf is part of the key.";
                ze:help "Routing instance the session runs in. The default instance is named default.";
            }
            leaf min-ttl {
                type uint8;
                default 254;
                description
                    "Ze discards a Control packet whose TTL is less than this value, and the test is
                    inclusive, so a TTL equal to it passes. A peer sends with a TTL of 255, so 254 allows
                    one router between the peer and Ze. Raise the value toward 255 when the peer is
                    fewer hops away, because a higher floor rejects a packet sent from further away.";
                ze:help "Minimum acceptable TTL on receive. Weak replacement
                         for GTSM on multi-hop paths.";
            }
            leaf profile {
                type leafref {
                    path "../../profile/name";
                    require-instance true;
                }
                description "Commit refuses a name that no profile declares, and names the profiles that
                    exist. Ze also refuses a profile that enables echo. Without this leaf the session takes the engine values: a detect
                    multiplier of 3, and 1000000 microseconds for both the transmit target and the
                    receive floor.";
                ze:help "Name of the timer profile this session takes its intervals from.";
            }
            leaf shutdown {
                type boolean;
                default false;
                description "The session stays configured and stops sending control packets, so a
                             peer sees it go down. Delete the list entry to remove it instead.";
                ze:help "Hold the session administratively down and keep its configuration.";
            }
        }
    }
}
