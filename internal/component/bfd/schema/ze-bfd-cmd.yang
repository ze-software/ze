module ze-bfd-cmd {
    namespace "urn:ze:bfd:cmd";
    prefix bfdcmd;
    import ze-extensions    { prefix ze; }
    import ze-cli-show-cmd  { prefix clishowcmd; }
    description
        "BFD session state, timers, and profile configuration.";
    revision 2026-04-11 {
        description "Initial revision (spec-bfd-4).";
    }

    augment "/clishowcmd:show" {
        container bfd {
            config false;
            description "BFD session state and timer configuration";

            container sessions {
                config false;
                ze:command "ze-bfd-api:show-sessions";
                description "List all active BFD sessions.
One line per session: peer address, state, negotiated tx/rx
intervals, and detect multiplier.";
            }

            container session {
                config false;
                description "Show one BFD session selected by peer address.";

                container address {
                    config false;
                    ze:command "ze-bfd-api:show-session";
                    description "Show full detail for one BFD session.
Pass the peer address. Returns local/remote discriminators,
negotiated timers, detection time, and packet counters.";
                    leaf address {
                        type string;
                        mandatory true;
                        description "Peer address";
                    }
                }
            }

            container profile {
                config false;
                ze:command "ze-bfd-api:show-profile";
                description "Show BFD timer profiles with effective values.
Returns min-tx, min-rx, and detect-multiplier after inheritance.
Use 'show bfd profile' for every profile or 'show bfd profile name <name>'
for one profile.";

                container name {
                    config false;
                    ze:command "ze-bfd-api:show-profile";
                    description "Show one BFD profile by name.";
                    leaf name {
                        type string;
                        mandatory true;
                        description "Profile name";
                    }
                }
            }
        }
    }
}
