module ze-isis-cmd {
    namespace "urn:ze:isis:cmd";
    prefix isiscmd;
    import ze-extensions { prefix ze; }
    description
        "show isis ... and clear isis ... command tree. Owned by the isis
         component so that removing it removes these command nodes together with
         the handlers in internal/component/isis/cmd_show.go. Both verbs bind into
         the CENTRAL ze-show / ze-clear command namespaces (Go-registered RPCs,
         the LDP/iface model); there is no per-component ze-isis-api module. The
         show and clear subtrees container-merge onto the generic show and clear
         verb roots. See ai/rules/plugin-self-containment.md.";
    revision 2026-06-18 {
        description "Initial revision: show isis neighbor/database[ detail]/route/interface/hostname/spf-log and clear isis adjacency/counters (spec-isis-13).";
    }

    container show {
        config false;
        description "Read-only commands to inspect system, protocol, and network state";

        container isis {
            config false;
            description "IS-IS neighbors, link-state database, routes, interfaces, hostnames, and SPF history (ISO/IEC 10589, RFC 1195).";

            container neighbor {
                config false;
                ze:command "ze-show:isis-neighbor";
                description "Show IS-IS adjacencies.
Returns the neighbor System ID, interface, level, adjacency state,
and hold time for each IS-IS neighbor.";
            }

            container database {
                config false;
                ze:command "ze-show:isis-database";
                description "Show the IS-IS link-state database.
Lists each LSP with its LSP ID, sequence number, remaining lifetime,
checksum, and overload bit, across Level-1 and Level-2.";

                container detail {
                    config false;
                    ze:command "ze-show:isis-database-detail";
                    description "Show the IS-IS link-state database with TLV detail.
Expands each LSP into its decoded TLVs (type, length, value) so you
can read exactly what each node advertises.";
                }
            }

            container route {
                config false;
                ze:command "ze-show:isis-route";
                description "Show IS-IS-computed routes.
Lists each prefix the SPF installed with its metric, level, up/down
bit, and next-hops (address and outgoing interface).";

                container ipv6 {
                    config false;
                    ze:command "ze-show:isis-route-ipv6";
                    description "Show IS-IS-computed IPv6 routes (RFC 5308).
Lists each IPv6 prefix the SPF installed with its metric, level,
and next-hops (link-local address and outgoing interface).";
                }
            }

            container interface {
                config false;
                ze:command "ze-show:isis-interface";
                description "Show IS-IS-enabled circuits.
Returns level, circuit type, metric, hello interval, hold multiplier,
passive flag, DIS state, and the count of Up adjacencies per circuit.";
            }

            container hostname {
                config false;
                ze:command "ze-show:isis-hostname";
                description "Show the IS-IS dynamic-hostname mapping (RFC 5301).
Maps each System ID to the hostname it advertises in TLV 137.";
            }

            container spf-log {
                config false;
                ze:command "ze-show:isis-spf-log";
                description "Show recent IS-IS SPF runs.
Returns the most recent SPF runs with their timestamp, level, trigger,
duration, and node count.";
            }
        }
    }

    container clear {
        config false;

        container isis {
            config false;
            description "Reset IS-IS runtime state without reconfiguring.";

            container adjacency {
                config false;
                ze:command "ze-clear:isis-adjacency";
                description "Tear down every IS-IS adjacency so neighbors re-form.
Usage: clear isis adjacency. Adjacencies re-learn from the next Hello;
the circuit is not closed and the configuration is unchanged.";
            }

            container counters {
                config false;
                ze:command "ze-clear:isis-counters";
                description "Reset IS-IS observational counters and the SPF log.
Usage: clear isis counters. Monotonic Prometheus series are not reset;
the SPF-run history is cleared.";
            }
        }
    }
}
