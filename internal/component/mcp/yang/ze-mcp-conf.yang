module ze-mcp-conf {
    namespace "urn:ze:mcp:conf";
    prefix mcp;

    import ze-types { prefix zt; }
    import ze-extensions { prefix ze; }

    description "MCP (Model Context Protocol) server configuration for Ze";

    revision 2026-04-19 {
        description "Add bind-remote, auth-mode, oauth, tls, identity[]. Legacy
                     token leaf preserved; maps to auth-mode=bearer for back-compat.";
    }

    revision 2026-01-01 {
        description "Initial revision";
    }

    container environment {
        description "The environment tree holds the settings of the services Ze runs, beside
the routing configuration rather than inside it.";
        ze:help "Environment settings of the MCP server.";

        container mcp {
            description "MCP is the Model Context Protocol. The Ze MCP server is the interface
an AI assistant uses to read state from Ze and to control it.";
            ze:help "Settings of the MCP server.";

            leaf enabled {
                type boolean;
                default false;
                description "The default is false, so Ze opens no MCP listener until this leaf
is true.";
                ze:help "Start the MCP server.";
            }

            leaf bind-remote {
                type boolean;
                default false;
                description "The default is false, which keeps the Phase 1 clamp. That clamp
forces every server entry to 127.0.0.1. When this leaf is true, Ze honors the ip the
operator configured, and auth-mode MUST be set to a value other than 'none'. The verify
step rejects a config that does not meet that condition.";
                ze:help "Allow the MCP server to bind to a non-loopback address.";
            }

            leaf auth-mode {
                type enumeration {
                    enum none {
                        ze:help "No authentication, permitted on a loopback bind only.";
                    }
                    enum bearer {
                        ze:help "One shared bearer token, read from the token leaf.";
                    }
                    enum bearer-list {
                        ze:help "One bearer token for each entry of the identity list.";
                    }
                    enum oauth {
                        ze:help "OAuth 2.1 resource server.";
                    }
                }
                description "In oauth mode, Ze validates a token locally against the JWKS of
the configured authorization server. If the token leaf is set and the auth-mode leaf is
absent, Ze infers 'bearer' for backward compatibility. In every other case the default
is 'none'.

bearer is the legacy mode, which reads one shared token from the token leaf. bearer-list
replaces it: each entry of the identity list names one principal and carries its own
token.";
                ze:help "Authentication strategy for the MCP server.";
            }

            leaf token {
                type string;
                ze:sensitive;
                description "When this leaf is set and no auth-mode leaf is present, Ze infers
auth-mode 'bearer'. Leave this leaf empty for bearer-list mode and for oauth mode.";
                ze:help "Bearer token for auth-mode=bearer.";
            }

            list identity {
                key "name";
                description "The token of each entry grants access to the named principal.
Authentication runs on every request, so the name and the scopes of the matching entry
ride that one authenticated request. Changing an identity, its token or its scopes
requires a daemon restart.";
                ze:help "Per-identity bearer entries, for auth-mode=bearer-list.";

                leaf name {
                    type string;
                    description "Ze writes the name to the log, and carries it on each request
the entry authenticates.";
                    ze:help "Name of the principal this entry authenticates.";
                }

                leaf token {
                    type string;
                    ze:sensitive;
                    description "Ze compares the token in constant time, so the duration of a
comparison tells an attacker nothing about the value.";
                    ze:help "Bearer token value of this identity.";
                }

                leaf-list scope {
                    type string;
                    description "This leaf-list is optional. An empty leaf-list carries no
scope.";
                    ze:help "Scopes Ze carries on a request this identity authenticates.";
                }
            }

            container oauth {
                description "Ze does not run an authorization server. Ze validates a bearer
token that the external authorization server issued.";
                ze:help "OAuth 2.1 resource-server settings, for auth-mode=oauth.";

                leaf authorization-server {
                    type string {
                        pattern '[hH][tT][tT][pP][sS]://[^?#]+';
                    }
                    description "The resource server inserts /.well-known/oauth-authorization-server
before the issuer URL's path (RFC 8414). The HTTPS metadata response must carry the
exact configured issuer and an HTTPS jwks_uri. Ze rejects redirects to HTTP.
Changing this setting on a running listener requires a restart.";
                    ze:help "HTTPS URL of the authorization server.";
                }

                leaf audience {
                    type string {
                        pattern '[hH][tT][tT][pP][sS]://[^#]+';
                    }
                    description "Ze compares the token's 'aud' claim with this identifier exactly,
without URL or Unicode normalization. Set this leaf explicitly to the HTTPS URL
clients use for the MCP endpoint. Ze never derives it from the request Host header.
Changing this setting on a running listener requires a restart.";
                    ze:help "Exact HTTPS identifier of this MCP endpoint.";
                }

                leaf-list required-scopes {
                    type string;
                    description "Ze rejects a token that does not carry every scope in this
list. An empty leaf-list accepts any valid token.";
                    ze:help "Scopes an accepted token MUST carry.";
                }
            }

            container tls {
                description "This container is required when auth-mode is oauth and a listen
endpoint is not a loopback address. ze config verify rejects a config that leaves the
cert leaf empty in that case, and one that sets cert without key.";
                ze:help "TLS certificate that serves the MCP endpoint over HTTPS.";

                leaf cert {
                    type string;
                    description "Ze serves the endpoint over HTTPS when cert and key are
                                 both set, and over HTTP when both are absent. A partial pair
                                 is rejected. Ze reads the pair at start and accepts TLS 1.2
                                 as its lowest version. Changing the pair requires a restart. A
                                 pair that fails to load stops the MCP server, and Ze prints the
                                 reason. ze doctor reads the file and reports it missing, or
                                 near its expiry date.";
                    ze:help "Path to PEM-encoded certificate file (or a chain).";
                }

                leaf key {
                    type string;
                    ze:sensitive;
                    description "Ze refuses a key file that group or other can read, and refuses
                                 a symbolic link, when it runs as a user other than root. The
                                 MCP server does not start in that case. Under root Ze reads the
                                 file whatever its mode, because root reads every file anyway.";
                    ze:help "Path to PEM-encoded private-key file.";
                }
            }

            list server {
                key "name";
                ze:listener;
                description "Each entry binds one address and one port. The address defaults
to 127.0.0.1 and the port defaults to 8080. The bind-remote leaf decides whether an
address other than loopback is kept.";
                ze:help "Listen endpoints of the MCP server.";

                leaf name {
                    type string;
                    description "The name is the list key, and it identifies the entry in the
configuration and in the log.";
                    ze:help "Name of this server instance.";
                }

                uses zt:listener {
                    refine ip {
                        default "127.0.0.1";
                    }
                    refine port {
                        default 8080;
                    }
                }
            }
        }
    }
}
