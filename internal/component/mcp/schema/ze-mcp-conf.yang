module ze-mcp-conf {
    namespace "urn:ze:mcp:conf";
    prefix mcp;

    import ze-types { prefix zt; }
    import ze-extensions { prefix ze; }

    description "MCP (Model Context Protocol) server configuration for Ze";

    revision 2026-01-01 {
        description "Initial revision";
    }

    container environment {
        description "Environment settings for MCP server";

        container mcp {
            description "MCP server settings (AI assistant control interface)";

            leaf enabled {
                type boolean;
                default false;
                description "Enable MCP server";
            }

            leaf token {
                type string;
                ze:sensitive;
                description "Bearer token for MCP authentication. When set, clients must send
                             Authorization: Bearer <token> header. Leave empty to allow
                             unauthenticated access (localhost-only).";
            }

            list server {
                key "name";
                ze:listener;
                description "MCP server listen endpoints";

                leaf name {
                    type string;
                    description "Server instance name";
                }

                uses zt:listener {
                    refine ip {
                        default "127.0.0.1";
                    }
                    refine port {
                        default 8080;
                    }
                }
            }
        }
    }
}
