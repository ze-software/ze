module ze-subscriber-cmd {
    namespace "urn:ze:subscriber:cmd";
    prefix subcmd;

    import ze-extensions    { prefix ze; }
    import ze-cli-show-cmd  { prefix clishowcmd; }

    description
        "Subscriber session overview and per-session detail.";

    revision 2026-05-22 {
        description "Initial revision (spec-subscriber-session-model).";
    }

    augment "/clishowcmd:show" {
        container subscriber {
            config false;
            ze:command "ze-l2tp:subscriber-summary";
            description "Counts by access type (PPPoE, L2TP, IPoE) with totals. It
is the quick way to see how many subscribers are online.";
            ze:help "Show a summary of all subscriber sessions.";

            container id {
                config false;
                description "The ID names one subscriber session. It is not the L2TP session identifier, which
                             show l2tp session takes.";
                ze:help "Select one subscriber session by ID.";

                container detail {
                    config false;
                    ze:command "ze-l2tp:subscriber-detail";
                    description "Pass the session ID. Returns access type, assigned
addresses, authentication state, uptime, and traffic counters.";
                    ze:help "Show everything about one subscriber session.";
                    leaf id {
                        type string;
                        mandatory true;
                        description "The id column of the show subscriber table. An L2TP session is named
l2tp-<tunnel-id>-<session-id> and a PPPoE session pppoe-<ifindex>-<session-id>. An
unknown id is refused with 'session not found'.";
                        ze:help "Subscriber session ID.";
                    }
                }
            }
        }
    }
}
