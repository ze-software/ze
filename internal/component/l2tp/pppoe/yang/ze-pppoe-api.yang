module ze-pppoe-api {
    namespace "urn:ze:pppoe:api";
    prefix pppoeapi;

    import ze-extensions { prefix ze; }

    description
        "PPPoE API operations for Ze. RPCs for observing session
         state and protocol counters. RFC 2516 supplies the field
         semantics (session ID, discovery tags).";

    revision 2026-05-08 {
        description "Initial PPPoE observability API (spec-bng-5-pppoe).";
    }

    rpc summary {
        description "The three numbers come from one snapshot, and the answer carries the time
that snapshot was taken. The command fails with pppoe: subsystem not running when PPPoE is
not started.";
        ze:help "Return subsystem summary: session count, interface count, aggregate state.";
        output {
            leaf summary {
                type string;
                description "The keys are session-count, interface-count and captured-at. Both counts
come from one snapshot, and captured-at is the UTC time of that snapshot in RFC 3339
form.";
                ze:help "JSON object with aggregate counters.";
            }
        }
    }

    rpc sessions {
        description "One snapshot answers every session. Each row carries the session id, the
client MAC address, the access interface, the service name, the state, the PPP unit and the
creation time.";
        ze:help "List every live PPPoE session across all interfaces.";
        output {
            leaf sessions {
                type string;
                description "Each object carries sid, mac, interface, service-name, state, unit and
created-at. state is discovery, session or teardown, and created-at is UTC in RFC 3339
form.";
                ze:help "JSON array of session objects.";
            }
        }
    }

    rpc session {
        description "The state is discovery, session or teardown. Session id 0 is refused
because RFC 2516 reserves it, and an id no session holds is reported as no session with that
sid.";
        ze:help "Return one session by session ID.";
        input {
            leaf session-id {
                type uint16;
                mandatory true;
                description "The identifier of one PPPoE session, as a decimal number. It is the sid
value of a 'sessions' row, and an unknown value is refused.";
                ze:help "PPPoE session ID (1..65535).";
            }
        }
        output {
            leaf session {
                type string;
                description "The object carries the same keys as one 'sessions' row: sid, mac,
interface, service-name, state, unit and created-at.";
                ze:help "JSON object with session detail.";
            }
        }
    }

    rpc statistics {
        description "The answer is the active session count and one row for each access
interface. Each row carries the interface name, its live session count and its configured
maximum.";
        ze:help "Return protocol counters: active sessions per interface, discovery packet counts.";
        output {
            leaf statistics {
                type string;
                description "The keys are sessions-active and interfaces. Each interfaces entry carries
interface, sessions and max-sessions.";
                ze:help "JSON object with counter values.";
            }
        }
    }

    rpc interfaces {
        description "Each row carries the interface name, its kernel index, its live session
count, its configured maximum and the service names it accepts.";
        ze:help "List configured PPPoE access interfaces.";
        output {
            leaf interfaces {
                type string;
                description "Each object carries name, ifindex, sessions, max-sessions and
service-names. service-names is an array of the Service-Name values the interface
accepts.";
                ze:help "JSON array of interface objects.";
            }
        }
    }
}
