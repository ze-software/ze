module ze-pppoe-cmd {
    namespace "urn:ze:pppoe:cmd";
    prefix pppoecmd;

    import ze-extensions    { prefix ze; }
    import ze-cli-show-cmd  { prefix clishowcmd; }

    description
        "PPPoE access concentrator sessions and statistics.";

    revision 2026-05-08 {
        description "Initial revision (spec-bng-5-pppoe).";
    }

    augment "/clishowcmd:show" {
        container pppoe {
            config false;
            ze:command "ze-l2tp:pppoe-summary";
            ze:rpc "ze-pppoe-api:summary";
            description "Without a subcommand, shows a summary of active
sessions.";
            ze:help "PPPoE session and protocol state.";

            container sessions {
                config false;
                ze:command "ze-l2tp:pppoe-sessions";
                ze:rpc "ze-pppoe-api:sessions";
                description "One line per session: session ID, MAC, subscriber
login, uptime, and assigned addresses.";
                ze:help "List all active PPPoE sessions.";
            }

            container session {
                config false;
                description "It takes a single session and prints everything the daemon holds for it. The list
                             of sessions is show pppoe session with no identifier.";
                ze:help "Show full detail for one PPPoE session.";

                container id {
                    config false;
                    ze:command "ze-l2tp:pppoe-session";
                    ze:rpc "ze-pppoe-api:session";
                    description "Pass the session ID. Returns discovery tags,
LCP/NCP state, assigned addresses, and traffic counters.";
                    ze:help "Show full detail for one PPPoE session.";
                    leaf id {
                        type string;
                        mandatory true;
                        description "The decimal sid column of the show pppoe session table. Zero is refused
because RFC 2516 reserves it, and an unknown id is refused with 'no session with sid'.";
                        ze:help "PPPoE session ID.";
                    }
                }
            }

            container statistics {
                config false;
                ze:command "ze-l2tp:pppoe-statistics";
                ze:rpc "ze-pppoe-api:statistics";
                description "Returns PADI, PADO, PADR, PADS, PADT counts, active
sessions, and errors. A rising PADI count with flat PADS means sessions are not
completing.";
                ze:help "Show PPPoE protocol message counters.";
            }

            container interfaces {
                config false;
                ze:command "ze-l2tp:pppoe-interfaces";
                ze:rpc "ze-pppoe-api:interfaces";
                description "Lists each PPPoE-enabled interface with its service
name, session limit, and how many sessions are active now.";
                ze:help "Show which interfaces are accepting PPPoE sessions.";
            }
        }
    }
}
