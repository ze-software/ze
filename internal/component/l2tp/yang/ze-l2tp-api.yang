module ze-l2tp-api {
    namespace "urn:ze:l2tp:api";
    prefix l2tpapi;

    import ze-extensions { prefix ze; }

    description
        "L2TP API operations for Ze. RPCs for observing tunnel and
         session state, bound listeners, effective configuration, and
         for operator-initiated teardown. RFC 2661 supplies the
         field semantics (tunnel/session state, AVP values).";

    revision 2026-10-21 {
        description "Declare l2tp-health, moved from ze-cli-show-api.";
    }

    revision 2026-04-17 {
        description "Initial L2TP observability + teardown API (spec-l2tp-7).";
    }

    // -----------------------------------------------------------------
    // Read operations (show l2tp ...). Every output value is a string
    // carrying the JSON payload; the CLI handler renders it directly.
    // -----------------------------------------------------------------

    rpc summary {
        description "The payload carries tunnel-count, session-count, listener-count, and
captured-at, which is the UTC time of the snapshot. When the L2TP subsystem is
not running, the RPC answers an error rather than a row of zeros.";
        ze:help "Return subsystem summary: tunnel count, session count, listener count, aggregate state.";
        output {
            leaf summary {
                type string;
                description "The keys are tunnel-count, session-count, listener-count and captured-at.
The counts come from one snapshot of the subsystem. captured-at is the UTC time
of that snapshot in RFC 3339 form.";
                ze:help "JSON object with aggregate counters.";
            }
        }
    }

    rpc tunnels {
        description "Each row is the summary form of one tunnel, and the 'tunnel' RPC returns the
detail form. Every row comes from one snapshot, so the whole table was read at
the same instant.";
        ze:help "List every live tunnel.";
        output {
            leaf tunnels {
                type string;
                description "Each object carries local-tid, remote-tid, peer, peer-hostname, state,
session-count, created-at, last-activity and max-sessions. last-activity is
empty when the tunnel has seen no activity. Timestamps are UTC in RFC 3339
form.";
                ze:help "JSON array of tunnel summary objects.";
            }
        }
    }

    rpc tunnel {
        description "The ID reaches the handler as the 'id' selector or as a bare argument, and both
forms parse the same way. The answer is the detail form of the tunnel rather
than the summary form 'tunnels' returns. An unknown ID is refused with 'no
tunnel with local-tid'.";
        ze:help "Return one tunnel by local tunnel ID.";
        input {
            leaf tunnel-id {
                type uint16;
                mandatory true;
                description "The ID Ze assigned to the tunnel, as a decimal number. It is the local-tid
value of a 'tunnels' row. Zero is refused because RFC 2661 reserves it.";
                ze:help "Local tunnel ID (1..65535).";
            }
        }
        output {
            leaf tunnel {
                type string;
                description "The object carries every field of a 'tunnels' row plus peer-framing,
peer-bearer, peer-recv-window and a sessions array. Each sessions entry is the
summary form of one session on that tunnel.";
                ze:help "JSON object with tunnel detail.";
            }
        }
    }

    rpc sessions {
        description "The rows are flattened across every tunnel, so a session's own tunnel is read
from the row and not from where the row sits. Each row is the summary form, and
the 'session' RPC returns the detail form.";
        ze:help "List every live session across all tunnels.";
        output {
            leaf sessions {
                type string;
                description "Each object carries local-sid, remote-sid, tunnel-local-tid, state, username,
assigned-addr, family and created-at. assigned-addr is empty when the session
holds no address. created-at is UTC in RFC 3339 form.";
                ze:help "JSON array of session summary objects.";
            }
        }
    }

    rpc session {
        description "The ID reaches the handler as the 'id' selector or as a bare argument. The
answer is the detail form of the session. An unknown ID is refused with 'no
session with local-sid'.";
        ze:help "Return one session by local session ID.";
        input {
            leaf session-id {
                type uint16;
                mandatory true;
                description "The ID Ze assigned to the session, as a decimal number. It is the local-sid
value of a 'sessions' row. Zero is refused because RFC 2661 reserves it.";
                ze:help "Local session ID (1..65535).";
            }
        }
        output {
            leaf session {
                type string;
                description "The object carries every field of a 'sessions' row plus tx-connect-speed,
rx-connect-speed, framing-type, sequencing-required, lns-mode and
kernel-setup-needed.";
                ze:help "JSON object with session detail.";
            }
        }
    }

    rpc statistics {
        description "The payload carries tunnels-active and sessions-active. Per-message counters are
not published here yet. Use 'listeners' for the bind state of each UDP endpoint.";
        ze:help "Return the L2TP protocol counters.";
        output {
            leaf statistics {
                type string;
                description "The keys are tunnels-active and sessions-active. Both come from one snapshot,
so they agree with each other and with 'summary'.";
                ze:help "JSON object with counter values.";
            }
        }
    }

    rpc listeners {
        description "Each row carries the bound address and the UDP port. An empty array means that
no listener is bound, which is the state 'summary' reports as a listener-count
of 0.";
        ze:help "List bound UDP listener endpoints.";
        output {
            leaf listeners {
                type string;
                description "Each object carries address and port. address is the bound IP address as
text, and port is the UDP port number.";
                ze:help "JSON array of listener objects.";
            }
        }
    }

    rpc config {
        description "Shared-secret is redacted to <set>/<unset>.";
        ze:help "Return effective runtime configuration.";
        output {
            leaf config {
                type string;
                description "The keys are enabled, max-tunnels, max-sessions, auth-method, allow-no-auth,
hello-interval, hello-retries, shared-secret and listeners. hello-interval is
in seconds, and listeners is an array of bound addresses as text.";
                ze:help "JSON object with effective config.";
            }
        }
    }

    // -----------------------------------------------------------------
    // Diagnostic operations (spec-diag-1-runtime-state).
    // -----------------------------------------------------------------

    rpc observer {
        description "With a session-id argument, returns the full event list. With
'all', returns a summary of every active session ring.";
        ze:help "Return per-session event ring snapshot.";
        input {
            leaf session-id {
                type uint16;
                description "A decimal local session ID selects the event ring of that one session.
'all' or no argument selects the summary of every ring. A session with no ring
is refused with 'no observer data'.";
                ze:help "Local session ID (1..65535), or omit for 'all'.";
            }
        }
        output {
            leaf observer {
                type string;
                description "With a session ID the object carries session-id, events and count. Each
event carries timestamp, type, tunnel-id and session-id, plus rtt-ms, actor,
reason and cause when set. With 'all' the object carries sessions and count,
and each entry carries session-id, event-count, last-event-type and
last-event-time.";
                ze:help "JSON object with events or session summaries.";
            }
        }
    }

    rpc cqm {
        description "With a login argument, returns the bucket list. With 'summary',
returns aggregate state across all tracked logins.";
        ze:help "Return per-login CQM bucket history.";
        input {
            leaf login {
                type string;
                description "A login name selects the bucket list of that one subscriber. 'summary',
'all' or no argument selects the per-login summary. A login with no CQM data
is refused with 'no CQM data'.";
                ze:help "Login name, or 'summary' for aggregate view.";
            }
        }
        output {
            leaf cqm {
                type string;
                description "With a login the object carries login, buckets and count. Each bucket
carries start, state, echo-count, min-rtt-ms, max-rtt-ms and avg-rtt-ms. With
'summary' the object carries logins and count, and each login carries
bucket-count, last-state, echo-count and avg-rtt-ms.";
                ze:help "JSON object with CQM buckets or login summaries.";
            }
        }
    }

    rpc echo {
        description "The state is derived from the CQM buckets and carries the last
RTT, the loss ratio, the echo interval, and the bucket state.";
        ze:help "Return the current echo state of one login.";
        input {
            leaf login {
                type string;
                mandatory true;
                description "The login name of the subscriber whose echo state is wanted. A login with
no echo data is refused with 'no echo data'.";
                ze:help "Login name.";
            }
        }
        output {
            leaf echo {
                type string;
                description "The keys are login, last-rtt-ms and bucket-state. echo-interval and
loss-ratio are present only when an echo interval is set for the login.";
                ze:help "JSON object with echo state.";
            }
        }
    }

    rpc reliable {
        description "The state carries Ns, Nr, peer-Nr, the outstanding count, the
retransmit count, cwnd, ssthresh, and the peer receive window size.";
        ze:help "Return the reliable transport window state of one tunnel.";
        input {
            leaf tunnel-id {
                type uint16;
                mandatory true;
                description "The ID Ze assigned to the tunnel whose control channel window is wanted, as
a decimal number. Zero is refused because RFC 2661 reserves it. An unknown ID
is refused with 'no tunnel with local-tid'.";
                ze:help "Local tunnel ID (1..65535).";
            }
        }
        output {
            leaf reliable {
                type string;
                description "The keys are tunnel-id, ns, nr, peer-nr, outstanding, retransmit-count,
cwnd, ssthresh and peer-rws. ns and nr are the next sequence numbers to send
and to receive, and peer-rws is the peer receive window size.";
                ze:help "JSON object with reliable transport state.";
            }
        }
    }

    rpc tunnel-history {
        description
            "Each transition carries the state it left, the state it reached, and a UTC
timestamp. A tunnel the subsystem holds no history for is refused with 'no
tunnel with local-tid'.";
        ze:help "Return FSM transition history for a tunnel.";
        input {
            leaf tunnel-id {
                type uint16;
                mandatory true;
                description "The ID Ze assigned to the tunnel whose transitions are wanted, as a decimal
number. Zero is refused because RFC 2661 reserves it.";
                ze:help "Local tunnel ID (1..65535).";
            }
        }
        output {
            leaf history {
                type string;
                description "The object carries transitions and count. Each transition carries from and
to, plus timestamp in UTC RFC 3339 form and trigger when they were recorded.";
                ze:help "JSON object with FSM transitions.";
            }
        }
    }

    rpc session-history {
        description
            "Each transition carries the state it left, the state it reached, and a UTC
timestamp. A session the subsystem holds no history for is refused with 'no
session with local-sid'.";
        ze:help "Return FSM transition history for a session.";
        input {
            leaf session-id {
                type uint16;
                mandatory true;
                description "The ID Ze assigned to the session whose transitions are wanted, as a
decimal number. Zero is refused because RFC 2661 reserves it.";
                ze:help "Local session ID (1..65535).";
            }
        }
        output {
            leaf history {
                type string;
                description "The object carries transitions and count. Each transition carries from and
to, plus timestamp in UTC RFC 3339 form and trigger when they were recorded.";
                ze:help "JSON object with FSM transitions.";
            }
        }
    }

    // -----------------------------------------------------------------
    // Destructive operations. All send either StopCCN (tunnel) or CDN
    // (session) with administrative Result Code and return a status
    // message.
    // -----------------------------------------------------------------

    rpc tunnel-teardown {
        description "The answer carries the tunnel ID and a status of 'sent', which reports that the
message left Ze and not that the peer answered. Use 'session-teardown' to stop
one session and leave the tunnel up.";
        ze:help "Send StopCCN Result Code 6 (administrative) for the tunnel with the given local tunnel ID.";
        input {
            leaf tunnel-id {
                type uint16;
                mandatory true;
                description "The ID Ze assigned to the tunnel to stop, as a decimal number. It is the
local-tid value of a 'tunnels' row. Zero is refused because RFC 2661 reserves
it.";
                ze:help "Local tunnel ID (1..65535).";
            }
        }
        output {
            leaf result {
                type string;
                description "The keys are action, tunnel-id and status. action is 'tunnel-teardown', and
status is 'sent' once the StopCCN has left Ze.";
                ze:help "JSON object describing the teardown outcome.";
            }
        }
    }

    rpc tunnel-teardown-all {
        description "The answer carries 'tunnels-cleared', the number of tunnels the subsystem tore
down. The RPC takes no input, so one named tunnel needs 'tunnel-teardown' with
its local tunnel ID.";
        ze:help "Send StopCCN Result Code 6 (administrative) for every live tunnel on every listener.";
        output {
            leaf result {
                type string;
                description "The keys are action and tunnels-cleared. action is 'tunnel-teardown-all',
and tunnels-cleared is a count that is 0 when no tunnel was live.";
                ze:help "JSON object with the number of tunnels torn down.";
            }
        }
    }

    rpc session-teardown {
        description "The answer carries the session ID and a status of 'sent', which reports that the
message left Ze and not that the peer answered. Optional actor, reason and cause
keywords are recorded against the session before the CDN goes out, and they are
echoed in the answer. The tunnel stays up.";
        ze:help "Send CDN Result Code 3 (administrative) for the session with the given local session ID.";
        input {
            leaf session-id {
                type uint16;
                mandatory true;
                description "The ID Ze assigned to the session to stop, as a decimal number. It is the
local-sid value of a 'sessions' row. Zero is refused because RFC 2661 reserves
it. The 'actor', 'reason' and 'cause' keywords after the ID are optional.";
                ze:help "Local session ID (1..65535).";
            }
        }
        output {
            leaf result {
                type string;
                description "The keys are action, session-id and status. action is 'session-teardown',
and status is 'sent' once the CDN has left Ze. reason and cause are present
when the request carried them.";
                ze:help "JSON object describing the teardown outcome.";
            }
        }
    }

    rpc session-teardown-all {
        description "The RPC sends CDN Result Code 3 (administrative) for each
session. The tunnels stay open.";
        ze:help "Stop every live session on every tunnel on every listener.";
        output {
            leaf result {
                type string;
                description "The keys are action and sessions-cleared. action is 'session-teardown-all',
and sessions-cleared is a count that is 0 when no session was live.";
                ze:help "JSON object with the number of sessions torn down.";
            }
        }
    }

    // -----------------------------------------------------------------
    // Operator-initiated calls (spec-followup-l2tp-call AC-4).
    // -----------------------------------------------------------------

    rpc outgoing-call {
        description "Dials the remote if no tunnel is up, sends OCRQ, and blocks
until the call establishes or fails. The response reports whether the call came
up and, on failure, the cause and RFC 2661 Result Code (tunnel authentication
reject, tie-breaker loss, peer CDN, or timeout). The named remote MUST have
outgoing-calls enabled.";
        ze:help "Place an LNS-side outgoing call toward a configured remote (RFC 2661 Section 10.4).";
        input {
            leaf remote {
                type string;
                mandatory true;
                description "The name of an l2tp/remote entry. The entry supplies the address and the
shared secret Ze dials with when no tunnel to that peer is up. An unknown name,
or an entry without outgoing-calls, is refused before any packet is sent.";
                ze:help "Name of a configured l2tp/remote dial target.";
            }
            leaf called {
                type string;
                mandatory true;
                description "The number the remote LAC dials, as free text. Ze copies it into the Called
Number AVP of the OCRQ without validation, so its form is what the LAC
accepts.";
                ze:help "Called Number placed in the OCRQ (RFC 2661 Section 7.9).";
            }
        }
        output {
            leaf result {
                type string;
                description "The keys are action, remote, called and established. A call that came up
adds local-sid and remote-sid. A call that failed adds error and, when the peer
or Ze supplied one, result-code.";
                ze:help "JSON object describing the call outcome.";
            }
        }
    }

    // show l2tp health (ze-l2tp:show-health) points at this rpc from
    // ze-l2tp-cmd; the handler is show_health.go.
    rpc l2tp-health {
        description "The rows are sorted by average round-trip time, highest first.
Each row carries the login, the last state, the echo count, the average
round-trip time in milliseconds and the bucket count. The degraded key counts
the logins whose last state is not established.";
        ze:help "Show L2TP session health sorted by echo loss.";
    }
}
