module ze-l2tp-conf {
    namespace "urn:ze:l2tp:conf";
    prefix l2tp;

    import ze-types { prefix zt; }
    import ze-extensions { prefix ze; }

    description "L2TPv2 (RFC 2661) subsystem configuration for Ze";

    revision 2026-04-15 {
        description "Split config: protocol settings at root l2tp{}, listeners under environment{l2tp{}}.";
    }

    container l2tp {
        description "L2TPv2 tunnel subsystem settings (RFC 2661).
                     Presence of this block with any content implies the
                     subsystem is enabled. Use 'enabled false' to disable
                     explicitly, or 'enabled true' as a filler when no
                     other settings are needed.";

        leaf enabled {
            type boolean;
            default true;
            description "Enable L2TP subsystem. Defaults to true when the
                         l2tp block is present; set to false to disable.";
        }

        leaf max-tunnels {
            type uint16;
            description
                "Maximum concurrent L2TP tunnels. A value of 0 (and the
                 unset default) means unbounded by this knob; the only
                 cap is the 65535 ceiling imposed by RFC 2661's 16-bit
                 Tunnel ID field. Set to a positive value to reject
                 further SCCRQs with StopCCN Result Code 2 once the
                 limit is reached.";
        }

        leaf max-sessions {
            type uint16;
            description
                "Maximum concurrent sessions per tunnel. A value of 0
                 (and the unset default) means unbounded. Set to a
                 positive value to reject further ICRQs and OCRQs with
                 CDN Result Code 4 (no resources) once the limit is
                 reached on any given tunnel.";
        }

        leaf shared-secret {
            type string;
            ze:sensitive;
            description
                "Shared secret used to compute CHAP-MD5 Challenge
                 Responses (RFC 2661 Section 4.2). When unset and a
                 peer sends a Challenge AVP, the subsystem rejects the
                 tunnel with StopCCN Result Code 4 (Not Authorized).
                 Value is masked in CLI output and cleared from the
                 process environment after first read.";
        }

        leaf hello-interval {
            type uint16 {
                range "1..3600";
            }
            description
                "Seconds of peer silence before sending HELLO. RFC 2661
                 recommends 60s; values above 3600 (one hour) are
                 rejected because they effectively disable keepalive.";
        }

        leaf cqm-enabled {
            type boolean;
            default false;
            description
                "Enable the CQM (Customer Quality Monitor) observer.
                 When true, pre-allocates per-session event rings and
                 per-login sample rings at subsystem start, and overrides
                 the PPP echo interval to 1s for RTT measurement.";
        }

        leaf max-logins {
            type uint32 {
                range "1..1000000";
            }
            default 1000;
            description
                "Maximum concurrent PPP logins tracked by the CQM observer.
                 Controls the size of the pre-allocated sample ring pool.
                 When exceeded, the least recently used login's data is evicted.";
        }

        leaf event-ring-size-per-session {
            type uint16 {
                range "16..4096";
            }
            default 256;
            description
                "Number of events in each per-session event ring.
                 When full, oldest events are overwritten.";
        }

        leaf sample-retention-seconds {
            type uint32 {
                range "100..86400";
            }
            default 86400;
            description
                "Duration of CQM sample retention per login, in seconds.
                 Divided by the 100-second bucket interval to determine
                 ring capacity. Default 86400 (24 hours) = 864 buckets.";
        }
    }

    container environment {
        description "Environment settings for L2TP subsystem";

        container l2tp {
            description "L2TP listener endpoints";

            list server {
                key "name";
                ze:listener;
                description "L2TP server listen endpoints (UDP)";

                leaf name {
                    type string;
                    description "Server instance name";
                }

                uses zt:listener {
                    refine ip {
                        default "0.0.0.0";
                    }
                    refine port {
                        default 1701;
                    }
                }
            }
        }
    }
}
