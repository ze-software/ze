module ze-l2tp-cmd {
    namespace "urn:ze:l2tp:cmd";
    prefix l2tpcmd;

    import ze-extensions    { prefix ze; }
    import ze-cli-show-cmd  { prefix clishowcmd; }
    import ze-cli-clear-cmd { prefix cliclearcmd; }

    description
        "L2TP tunnel and session operations for BNG subscriber access.
         Adds 'show l2tp' commands for inspection, 'clear l2tp' commands
         for teardown, and 'request l2tp' operator actions.";

    revision 2026-10-21 {
        description "show l2tp health points at l2tp-health in ze-l2tp-api, its owner.";
    }

    revision 2026-07-10 {
        description "Add 'request l2tp outgoing-call remote <name> called <number>' (spec-followup-l2tp-call AC-4).";
    }

    revision 2026-06-03 {
        description "Relocate show l2tp-health from central show schema (plugin self-containment).";
    }

    revision 2026-04-22 {
        description "Move destructive tree from top-level l2tp to clear verb (spec-l2tp-11-web).";
    }

    revision 2026-04-17 {
        description "Initial revision (spec-l2tp-7-subsystem).";
    }

    // -----------------------------------------------------------------
    // Read tree: `show l2tp ...`
    // -----------------------------------------------------------------
    augment "/clishowcmd:show" {
        container l2tp {
            config false;
            ze:command "ze-l2tp:summary";
            ze:rpc "ze-l2tp-api:summary";
            description "Without a subcommand, shows a summary of tunnels and
sessions.";
            ze:help "L2TP tunnel, session, and subscriber state.";

            container health {
                config false;
                ze:command "ze-l2tp:show-health";
                ze:rpc "ze-l2tp-api:l2tp-health";
                description "Sorts sessions by echo loss ratio (worst first). Shows
subscriber login, session state, echo count, average RTT, and CQM bucket count.
Reports how many sessions are degraded.";
                ze:help "Find your worst L2TP sessions at a glance.";
            }

            container tunnels {
                config false;
                ze:command "ze-l2tp:tunnels";
                ze:rpc "ze-l2tp-api:tunnels";
                description "One line per tunnel: local/remote ID, peer address,
session count, and uptime.";
                ze:help "List all active L2TP tunnels.";
            }

            container tunnel {
                config false;
                description "It takes a single tunnel and prints everything the daemon holds for it, including
                             the sessions it carries.";
                ze:help "Show full detail for one L2TP tunnel.";

                container id {
                    config false;
                    ze:command "ze-l2tp:tunnel";
                    ze:rpc "ze-l2tp-api:tunnel";
                    description "Pass the local tunnel ID. Returns control channel
state, peer endpoint, hello interval, and all assigned sessions.";
                    ze:help "Show full detail for one L2TP tunnel.";
                    leaf id {
                        type string;
                        mandatory true;
                        description "The decimal local tunnel ID from the show l2tp tunnel table. Zero is
refused because RFC 2661 reserves it, and an unknown ID is refused with 'no tunnel with
local-tid'.";
                        ze:help "Local tunnel ID.";
                    }
                }

                container history {
                    config false;
                    ze:command "ze-l2tp:tunnel-history";
                    ze:rpc "ze-l2tp-api:tunnel-history";
                    description "Timestamped FSM entries showing how the tunnel
reached its current state. Use this to diagnose a tunnel establishment
failure.";
                    ze:help "Show state transitions for a tunnel over time.";
                }
            }

            container sessions {
                config false;
                ze:command "ze-l2tp:sessions";
                ze:rpc "ze-l2tp-api:sessions";
                description "One line per session: local/remote ID, parent tunnel,
subscriber login, and uptime.";
                ze:help "List all active L2TP sessions.";
            }

            container session {
                config false;
                description "It takes a single session and prints everything the daemon holds for it. The list
                             of sessions is show l2tp session with no identifier.";
                ze:help "Show full detail for one L2TP session.";

                container id {
                    config false;
                    ze:command "ze-l2tp:session";
                    ze:rpc "ze-l2tp-api:session";
                    description "Pass the local session ID. Returns PPP state,
assigned addresses, negotiated LCP/NCP options, and traffic counters.";
                    ze:help "Show full detail for one L2TP session.";
                    leaf id {
                        type string;
                        mandatory true;
                        description "The decimal local session ID from the show l2tp session table. Zero is
refused because RFC 2661 reserves it, and an unknown ID is refused with 'no session with
local-sid'.";
                        ze:help "Local session ID.";
                    }
                }

                container history {
                    config false;
                    ze:command "ze-l2tp:session-history";
                    ze:rpc "ze-l2tp-api:session-history";
                    description "Timestamped FSM entries for session establishment.
Use this when a subscriber's session fails to come up.";
                    ze:help "Show state transitions for a session over time.";
                }

                container traffic {
                    config false;
                    ze:command "ze-l2tp:session-traffic";
                    description "Returns byte and packet counts, error counters, and
current rates. Compare with CQM data to get the full picture of subscriber
health.";
                    ze:help "Show traffic counters for a subscriber's PPP interface.";
                }
            }

            container statistics {
                config false;
                ze:command "ze-l2tp:statistics";
                ze:rpc "ze-l2tp-api:statistics";
                description "Tunnels and sessions established, control messages
sent and received, retransmits, and errors. It is the first command to run for
L2TP health.";
                ze:help "Show aggregate L2TP protocol counters.";
            }

            container listeners {
                config false;
                ze:command "ze-l2tp:listeners";
                ze:rpc "ze-l2tp-api:listeners";
                description "Lists each bound address, port, and the number of
tunnels on it.";
                ze:help "Show which UDP sockets are listening for L2TP.";
            }

            container config {
                config false;
                ze:command "ze-l2tp:config";
                ze:rpc "ze-l2tp-api:config";
                description "Returns the effective config after defaults and
overrides. Confirms what the daemon uses.";
                ze:help "Show the resolved L2TP configuration.";
            }

            container observer {
                config false;
                ze:command "ze-l2tp:observer";
                ze:rpc "ze-l2tp-api:observer";
                description "Returns the event ring buffer for one session ID or
'all'. Use it to find why a session failed to establish.";
                ze:help "Show recent events for a session (debug aid).";
            }

            container cqm {
                config false;
                ze:command "ze-l2tp:cqm";
                ze:rpc "ze-l2tp-api:cqm";
                description "Pass a login name for one subscriber or 'summary' for
an overview. Use it to diagnose a poor subscriber experience.";
                ze:help "Show subscriber line quality (CQM latency buckets).";
            }

            container echo {
                config false;
                ze:command "ze-l2tp:echo";
                ze:rpc "ze-l2tp-api:echo";
                description "Returns echo request and reply counters and round-trip
times. Rising loss or high RTT indicates a degraded line.";
                ze:help "Show LCP echo health for a subscriber session.";
            }

            container reliable {
                config false;
                ze:command "ze-l2tp:reliable";
                ze:rpc "ze-l2tp-api:reliable";
                description "Returns send and receive sequence numbers, window size,
and retransmit queue depth. Check here when tunnel control messages stop
moving.";
                ze:help "Show the reliable transport window for a tunnel.";
            }
        }
    }

    // -----------------------------------------------------------------
    // Destructive tree: `clear l2tp tunnel {id <id> | all}`, `clear l2tp
    // session {id <id> | all}`. Under `clear` verb because they reset
    // runtime/operational state without touching config.
    // -----------------------------------------------------------------
    augment "/cliclearcmd:clear" {
        container l2tp {
            config false;
            description "A tunnel torn down takes every session it carries with it, so clear l2tp tunnel
                         is the wider of the two. Neither one edits the configuration, and a peer that is
                         configured to reconnect will.";
            ze:help "Tear down L2TP tunnels and sessions.";

            container tunnel {
                config false;
                description "Every session the tunnel carries goes with it. Use clear l2tp session to drop one
                             call and leave the tunnel up.";
                ze:help "Tear down L2TP tunnels.";

                container id {
                    config false;
                    ze:command "ze-l2tp:tunnel-teardown";
                    ze:rpc "ze-l2tp-api:tunnel-teardown";
                    description "Sends a StopCCN to the peer. Every session on this
tunnel is disconnected. Pass the local tunnel ID: clear l2tp tunnel id
<id>.";
                    ze:help "Gracefully tear down one L2TP tunnel.";
                }

                container all {
                    config false;
                    ze:command "ze-l2tp:tunnel-teardown-all";
                    ze:rpc "ze-l2tp-api:tunnel-teardown-all";
                    description "Sends StopCCN for all tunnels. Every subscriber
session is disconnected. Use with care during maintenance.";
                    ze:help "Tear down every L2TP tunnel on this box.";
                }
            }

            container session {
                config false;
                description "The tunnel that carried the session stays open. The peer can place a new
                             call, and it does not negotiate the tunnel again.";
                ze:help "Tear down L2TP sessions.";

                container id {
                    config false;
                    ze:command "ze-l2tp:session-teardown";
                    ze:rpc "ze-l2tp-api:session-teardown";
                    description "Sends a CDN to gracefully close the session. Pass
the local session ID: clear l2tp session id <id> [reason <text>] [cause
<code>].";
                    ze:help "Disconnect one subscriber session.";
                }

                container all {
                    config false;
                    ze:command "ze-l2tp:session-teardown-all";
                    ze:rpc "ze-l2tp-api:session-teardown-all";
                    description "Sends CDN for all sessions across all tunnels. The
tunnels stay up. Use with care.";
                    ze:help "Disconnect every L2TP session on this box.";
                }
            }
        }
    }

    // -----------------------------------------------------------------
    // Operator action tree: `request l2tp outgoing-call remote <name>
    // called <number>`. Under the `request` verb because it performs a
    // runtime operational action (dial-out) without touching config.
    // Two typed selectors (remote, called) nest as a container per
    // keyword, with both leaves on the final ze:command node so each is
    // captured into ctx.Selectors (ai/rules/cli-grammar.md).
    // -----------------------------------------------------------------
    container request {
        config false;

        container l2tp {
            config false;
            description "These drive the protocol on the live daemon. Nothing here writes configuration, so
                         the actions are lost across a restart.";
            ze:help "L2TP operator actions (RFC 2661).";

            container outgoing-call {
                config false;
                description "Ze acts as the LNS and asks the LAC to dial, which is the OCRQ direction of RFC
                             2661. The remote must already be configured: this command selects one, it does not
                             define one.";
                ze:help "Place an LNS-side outgoing call toward a remote.";

                container remote {
                    config false;
                    description "The name is one the configuration already declares. An unknown name is refused
                                 rather than dialed, so a typo cannot open a call to an unintended peer.";
                    ze:help "Select the configured remote to dial.";

                    container called {
                        config false;
                        ze:command "ze-l2tp:outgoing-call";
                        ze:rpc "ze-l2tp-api:outgoing-call";
                        description "Dials the named remote (which must have
outgoing-calls enabled), sends OCRQ, and blocks until the call establishes or
fails. On failure the cause and RFC 2661 Result Code are reported (auth reject,
tie-breaker loss, peer CDN, or timeout).";
                        ze:help "Place an LNS-side outgoing call (RFC 2661 S10.4).";
                        leaf remote {
                            type string;
                            mandatory true;
                            description "The name of an l2tp/remote entry, which supplies the address and the
shared secret Ze dials with. An unknown name, or an entry without outgoing-calls, is
refused before any packet is sent.";
                            ze:help "Configured l2tp/remote dial-target name.";
                        }
                        leaf called {
                            type string;
                            mandatory true;
                            description "The number the remote LAC dials, as free text. Ze copies it into the
Called Number AVP of the OCRQ without validation, so its form is what the LAC accepts.";
                            ze:help "Called Number for the OCRQ.";
                        }
                    }
                }
            }
        }
    }
}
