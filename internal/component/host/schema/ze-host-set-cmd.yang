module ze-host-set-cmd {
    namespace "urn:ze:host:set:cmd";
    prefix hostsetcmd;
    import ze-extensions { prefix ze; }
    description "set system file-descriptors command. Owned by the host component because it adjusts process resource limits (setrlimit). See ai/rules/plugin-self-containment.md.";
    revision 2026-06-06 { description "Relocated set system file-descriptors out of the central set schema (plugin self-containment)."; }

    container set {
        config false;
        description "Modify running configuration parameters";

        container system {
            config false;
            description "System-level runtime tunables";

            container file-descriptors {
                config false;
                ze:command "ze-set:system-file-descriptors";
                description "Raise the file descriptor limit for the daemon process.
Pass a number or 'max' to go to the hard limit. Takes effect
immediately. Check current limits with 'show system file-descriptors'.";
                leaf limit {
                    type union {
                        type uint64;
                        type enumeration {
                            enum max;
                        }
                    }
                    description "New limit or max for hard limit";
                }
            }
        }
    }
}
