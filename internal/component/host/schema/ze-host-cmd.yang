module ze-host-cmd {
    namespace "urn:ze:host:cmd";
    prefix hostcmd;
    import ze-extensions { prefix ze; }
    description "show host / show system kernel-log command tree. Owned by the host component because these handlers read hardware inventory (host.DetectSection) and kernel log (/dev/kmsg). See ai/rules/plugin-self-containment.md.";
    revision 2026-06-06 { description "Relocated show host and show system kernel-log out of the central show schema (plugin self-containment)."; }

    container show {
        config false;
        description "Read-only commands to inspect system, protocol, and network state";

        container host {
            config false;
            description "Hardware inventory for this box.
Sections: cpu, nic, dmi, memory, thermal, storage, kernel, platform.
Use a subcommand for one section, or 'show host all' for everything.";

            container cpu {
                config false;
                ze:command "ze-show:host-cpu";
                description "Show what CPUs are in this box.
Returns vendor, model, core/thread topology, hybrid layout, scaling
driver, current/min/max frequencies, and throttle counts.";
            }

            container nic {
                config false;
                ze:command "ze-show:host-nic";
                description "Show physical NICs installed in this box.
Returns driver, PCI vendor/device IDs, link speed, queue counts, and
firmware version. Virtual interfaces are excluded. Use this to confirm
NIC firmware before an upgrade.";
            }

            container dmi {
                config false;
                ze:command "ze-show:host-dmi";
                description "Show the box's identity from SMBIOS/DMI.
Returns system vendor, board name, BIOS version, and chassis type.
Useful for inventory or confirming which hardware model you are on.";
            }

            container memory {
                config false;
                ze:command "ze-show:host-memory";
                description "Show installed memory and ECC health.
Returns DIMM sizes and, when the edac driver is present, correctable
and uncorrectable error counters. Non-zero ECC counts mean you should
plan a DIMM replacement.";
            }

            container thermal {
                config false;
                ze:command "ze-show:host-thermal";
                description "Show temperature sensors and thermal throttle events.
Returns hwmon sensor readings and per-CPU throttle counters. Non-zero
throttle counts mean the box has been running hot enough to slow down.";
            }

            container storage {
                config false;
                ze:command "ze-show:host-storage";
                description "Show storage devices attached to this box.
Returns size, model, transport type (nvme, sata, mmc, virtio),
rotational flag, and NVMe firmware version where applicable.";
            }

            container kernel {
                config false;
                ze:command "ze-show:host-kernel";
                description "Show the running kernel version and boot parameters.
Returns kernel release, command line, CPU microcode revision, boot
time, and security-relevant CPU flags (spectre mitigations, etc.).";
            }

            container platform {
                config false;
                ze:command "ze-show:host-platform";
                description "Show platform capabilities and constraints.
Reports read-only root, privilege level, systemd presence, gokrazy
update socket, reboot-allowed flag, persistent-storage writability,
and fd limits. Helps you understand what operations are possible
on this particular deployment.";
            }

            container all {
                config false;
                ze:command "ze-show:host-all";
                description "Show the full hardware inventory in one shot.
Returns every section (cpu, nic, dmi, memory, thermal, storage,
kernel, platform) as a single JSON response. Ideal for support
bundles or automated inventory collection.";
            }
        }

        container system {
            config false;
            description "System-level status and diagnostics";

            container kernel-log {
                config false;
                ze:command "ze-show:system-kernel-log";
                description "Show kernel log messages (dmesg-style).
Reads from /dev/kmsg. Filter by syslog level (emerg through debug)
and limit with count. Without count, you get everything available.
Linux only. Useful for spotting NIC errors or OOM events.";
                leaf level {
                    type enumeration {
                        enum emerg;
                        enum alert;
                        enum crit;
                        enum err;
                        enum warn;
                        enum notice;
                        enum info;
                        enum debug;
                    }
                    description "Filter by syslog level";
                }
                leaf count {
                    type uint32;
                    description "Maximum number of messages";
                }
            }
        }
    }
}
