module ze-hub-conf {
    namespace "urn:ze:hub:conf";
    prefix hub;

    import ze-extensions { prefix ze; }

    description "Hub/core configuration for ZeBGP";

    revision 2026-01-01 {
        description "Initial revision";
    }

    // Environment block - ZeBGP-specific settings
    container environment {
        description "Ze copies each leaf in this block into an environment variable at config load. The OS
            environment wins: a variable already set there keeps its value, and the leaf is ignored. Ze
            also refuses to overwrite a variable it set itself. A changed leaf therefore reaches the
            runtime at the next daemon start, and not at a reload.";
        ze:help "ZeBGP environment settings";

        container daemon {
            description "The container holds the path of the PID file and the user Ze changes to. Ze reads
                both leaves at startup, in that order, and neither one changes a running daemon.";
            ze:help "Daemon settings";

            leaf pid {
                type string;
                description "Ze writes its own process ID to this path at startup and removes the file at a
                    clean shutdown. The create refuses an existing file, so a second daemon that names
                    the same path stops at startup with an error. When the user leaf is also set, Ze
                    gives the file to that user, because the shutdown path runs after the change of user.
                    Ze writes no PID file while the leaf is absent.";
                ze:help "PID file path";
            }

            leaf user {
                type string;
                default "zeuser";
                description "Ze starts as root to bind port 179, then changes to this user before it starts a
                    plugin or accepts a connection. A user name and a numeric UID are both accepted, and
                    the user's primary group is used. Ze keeps root while the leaf is absent.";
                ze:help "System user for privilege drop";
            }
        }

        container log {
            description "A name this container does not declare becomes a subsystem level: bgp.routes debug
                sets the level of the bgp.routes subsystem alone. Ze reads a subsystem level from the
                longest matching name to the shortest, so bgp covers bgp.fsm until bgp.fsm is set too.";
            ze:help "Logging settings";

            // Base log level for all subsystems (ze.log)
            leaf level {
                type string;
                default "INFO";
                description "warn is the level Ze uses while no config leaf and no environment variable set
                    one. warning, error and err name the same two levels, and disabled silences every
                    subsystem. Ze refuses any other word with a warning on stderr and keeps the level it
                    already has. A subsystem name written beside this leaf overrides it for that
                    subsystem alone.";
                ze:help "Base log level for all subsystems: disabled, debug, info, warn, or err (case-insensitive)";
            }

            // Log output backend
            leaf backend {
                type enumeration {
                    enum stderr { ze:help "Standard error output"; }
                    enum stdout { ze:help "Standard output"; }
                    enum syslog { ze:help "Syslog daemon"; }
                }
                description "syslog reads the destination leaf for its address, and it is the one value that
                    does not write to a file descriptor. Ze writes to stderr when the syslog dial fails,
                    and also while the leaf is absent.";
                ze:help "Log output backend (default: stderr)";
            }

            // Syslog destination address
            leaf destination {
                type string;
                default "stdout";
                description "An empty value reaches the local syslog daemon. A value that starts with /
                    names a Unix socket. Any other value is a UDP address, so 127.0.0.1:514 sends to a
                    collector on this host. Ze writes to stderr when the dial fails. The crash log reads
                    the same address, and it reads it once at startup.";
                ze:help "Syslog address used when backend is syslog: empty, a socket path, or host:port";
            }

            // Plugin stderr relay level
            leaf relay {
                type string;
                description "A plugin runs as its own process and writes to its own stderr. Ze relays a line
                    at this level or above into its own log, and drops the rest. warn is the level Ze
                    uses while the leaf is absent, and disabled silences a plugin's stderr completely.";
                ze:help "Plugin stderr relay level: disabled, debug, info, warn, or err (case-insensitive)";
            }

            leaf color {
                type boolean;
                description "NO_COLOR and TERM=dumb win over this leaf, and each one removes color whatever
                    the leaf holds. While neither is set and the leaf is absent, Ze writes color only
                    when the log writer is a terminal.";
                ze:help "Force color log output on (true) or off (false). When unset, auto-detected from terminal.";
            }

            // Subsystem-specific log levels (any key allowed)
            // Syntax: <subsystem-path> <level>;
            // Example: bgp.routes debug;
            // Maps to: ze.log.bgp.routes=debug
            ze:allow-unknown-fields;
        }

        // pprof HTTP server address (top-level leaf under environment).
        // Consumed by startPprofServer via env var `ze.pprof`.
        leaf pprof {
            type string;
            description "Ze starts the Go pprof handlers on this address at startup. The host must be
                127.0.0.1, ::1 or localhost, and Ze stops with an error for any other host. An address
                that carries no host, such as :6060, binds every interface, so Ze stops on it too. Ze
                starts no pprof server while the leaf is absent. When the ze command line gives a
                pprof address, Ze uses that address and ignores this leaf.";
            ze:help "Address of the pprof HTTP server, which must be a loopback address";
        }

        // Management hardening: the X-Ze-Version banner both HTTP servers send.
        // Consumed by version.HTTPHeaderHidden via env var `ze.hide-version`.
        leaf hide-version {
            type boolean;
            default false;
            description "The web interface and the looking glass both stamp X-Ze-Version on a
                response. The banner gives the release, the git commit, the Go version and the
                OS, which tells a client the exact build it speaks to. With true, neither
                server sends the header, and no other header changes. The default false keeps
                the banner, so a tool that reads it continues to operate. Ze reads the leaf at
                startup, so a new value applies at the next daemon start.";
            ze:help "Hide the X-Ze-Version banner on every HTTP response (ze.hide-version)";
        }

        container chaos {
            description "Ze wraps the clock, the dialer and the listener factory with a fault injector while
                seed is not 0. The block exists to test Ze against slow timers and failed connections.
                A production config leaves the block out.";
            ze:help "Chaos fault injection settings";

            leaf seed {
                type int64;
                description "Ze builds the fault injector only while the seed is not 0. The same seed replays
                    the same sequence of faults, so a failed run can be repeated. A seed of -1 takes the
                    seed from the clock, and Ze logs the value it took. Ze applies the ze command line
                    after the config load, so a seed given there replaces the seed in this leaf.";
                ze:help "PRNG seed (0 = disabled)";
            }

            leaf rate {
                type string;
                default "0.1";
                description "0.1 injects a fault into one operation in ten. Ze uses 0.1 for a value that is
                    not a number, and for a value outside 0.0 to 1.0. The leaf does nothing while seed
                    is 0.";
                ze:help "Fault probability per operation (0.0-1.0)";
            }
        }

        container cli {
            description "The container holds the default output format and the transcript switch. Both leaves
                apply to every CLI session this daemon serves.";
            ze:help "CLI session settings";
            container format {
                description "The container holds the default leaf alone. A session overrides it with set cli
                    format, which changes that one session and no other.";
                ze:help "Default output format settings";
                leaf default {
                    type enumeration {
                        enum text { ze:help "Space-aligned columns without box-drawing"; }
                        enum table { ze:help "Nushell-style table with box-drawing characters"; }
                        enum json { ze:help "JSON output (pretty-printed)"; }
                        enum yaml { ze:help "YAML output"; }
                        enum ndjson { ze:help "Newline-delimited JSON (one object per line)"; }
                    }
                    default "text";
                    description "text writes space-aligned columns, table draws a box around them, json
                        pretty-prints, yaml writes YAML, and ndjson writes one JSON object on each line.
                        A format operator on the command line, such as | json, wins over this leaf, and
                        so does set cli format. Ze falls back to text for a value it does not know.";
                    ze:help "Default output format when no pipe operator is specified";
                }
            }
            leaf transcript {
                type enumeration {
                    enum enabled { ze:help "Record CLI session commands and output to local transcript file"; }
                    enum disabled { ze:help "No transcript recording"; }
                }
                default "disabled";
                description "enabled writes one file for each session, named transcript-DATE-TIME-PID.log,
                    with mode 0600 in a directory with mode 0700. Each entry holds the time, the command
                    with its pipe operators, and the answer. Ze writes under $HOME/.local/share while
                    XDG_DATA_HOME is unset, and it reports a directory it cannot create on stderr.";
                ze:help "CLI session transcript recording to $XDG_DATA_HOME/ze/transcripts/";
            }
        }

        container exabgp {
            description "The bridge runs an unchanged ExaBGP API program against Ze, and the container holds
                the settings of the channel to that program.";
            ze:help "ExaBGP compatibility settings for the migration bridge";
            container api {
                description "The container holds the ack and version leaves. The bridge reads them once, when
                    it starts, so a change reaches the bridge at the next daemon start.";
                ze:help "ExaBGP bridge API settings";
                leaf ack {
                    type boolean;
                    default true;
                    description "true matches ExaBGP, and it lets the program wait for done before it sends
                        the next command. false keeps the bridge silent, and a program that waits for
                        done then stops. The bridge reads false, 0, no, off, disable and disabled as
                        false, and every other value as true.";
                    ze:help "Emit done/error ack lines on plugin stdin after each dispatched command";
                }
                leaf version {
                    type enumeration {
                        enum auto { ze:help "Detect each script's API version from its commands."; }
                        enum "4" { ze:help "Hold every script to the ExaBGP 4.x and 5.x API."; }
                        enum "6" { ze:help "Hold every script to the ExaBGP 6.0 API, JSON only."; }
                    }
                    default auto;
                    description "ExaBGP's api.version. auto holds each script to the API of the first
                        command that tells: 'peer ...' is 6, 'announce ...' or 'neighbor ...' is 4. 4 or 6
                        holds every script to that API from its start. A script held to one API is
                        answered error for a command of the other. A script's 'api version <v>' line moves
                        the setting for the scripts started afterwards.";
                    ze:help "ExaBGP API version of the bridge's scripts: auto, 4 or 6";
                }
            }
        }
    }
}
