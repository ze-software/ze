module ze-plugin-show {
    namespace "urn:ze:plugin:show";
    prefix plugshow;
    import ze-extensions { prefix ze; }
    description "show plugins command tree. Owned by internal/component/plugin because the handler reads the internal plugin registry. See ai/rules/plugins.md. Named ze-plugin-show rather than ze-plugin-cmd because internal/core/ipc/yang already declares a module of that name, under the same namespace, for the plugin help, command and session trees. Two modules sharing a namespace is the collision YANG namespaces exist to prevent, and a loader can accept it quietly rather than refusing, which leaves nobody able to say which module a node came from.";
    revision 2026-08-31 { description "Carry the setup outcome each plugin recorded from its own init() on the show plugins rows."; }
    revision 2026-08-30 { description "Declare show plugins, the command that replaces the root plugin-listing flag."; }

    container show {
        config false;
        description "Read-only commands to inspect system, protocol, and network state.";

        container plugins {
            config false;
            ze:command "ze-show:plugins";
            description "List the plugins compiled into this binary.";
            ze:help "Each row carries the plugin name, what it does, the address
families it handles, the RFCs it implements, the BGP capability codes it owns,
the setup outcome its own init() recorded (succeeded, soft-failure,
hard-failure or unknown) and the reason the plugin gave. A plugin that
recorded nothing is listed as unknown, never omitted, and a plugin that
recorded and then did not register keeps its row.
The outcome replays a past event: it was recorded once, before main(),
and this command reads it back. 'show health' answers the other question,
by running a probe now and reporting what the daemon is doing at this
moment.";
        }
    }
}
