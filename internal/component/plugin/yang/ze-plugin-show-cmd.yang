module ze-plugin-show-cmd {
    namespace "urn:ze:plugin:show";
    prefix plugshow;
    import ze-extensions { prefix ze; }
    description "show plugin command tree. Owned by internal/component/plugin because the handlers read the internal plugin registry. See ai/rules/plugins.md. The name ends in -cmd because that suffix is how a command tree is found: BuildCommandTree (internal/component/config/yang/command.go) merges only the modules whose name carries it, so a module outside that set puts no node in the CLI tree and no row in the command contract. It is ze-plugin-show-cmd rather than ze-plugin-cmd because internal/core/ipc/yang already declares a module of that name, for the plugin help, command and session trees. Two modules with one name is a collision a loader can accept quietly rather than refuse, which leaves nobody able to say which module a node came from.";
    revision 2026-09-09 { description "Declare show plugin declarations, which answers what each plugin declares. show plugin list answers which plugins the binary carries, so the two actions sit on one noun."; }
    revision 2026-09-08 { description "Spell the enumerating action list: the command is show plugin list. The module name gains the -cmd suffix the command-tree loader discovers, which the show plugins spelling never had."; }
    revision 2026-08-31 { description "Carry the setup outcome each plugin recorded from its own init() on the show plugin list rows."; }
    revision 2026-08-30 { description "Declare the command that replaces the root plugin-listing flag."; }

    container show {
        config false;
        ze:help "Read-only commands to inspect system, protocol, and network state.";

        container plugin {
            config false;
            description "It reports the plugins this binary carries. It reads a registry the
process filled before main(), so it answers with no daemon running.";
            ze:help "Plugin inspection.";

            container list {
                config false;
                ze:command "ze-plugin:show-list";
                description "Each row carries the plugin name, what it does, the address
families it handles, the RFCs it implements, the BGP capability codes it owns,
the config roots that load it, the plugins it depends on, uses when present or
starts after, its features, whether it carries a YANG schema, an NLRI decoder
or an NLRI encoder, the setup outcome its own init() recorded (succeeded, soft-failure,
hard-failure or unknown) and the reason the plugin gave. A plugin that
recorded nothing is listed as unknown, never omitted, and a plugin that
recorded and then did not register keeps its row.
The outcome replays a past event: it was recorded once, before main(),
and this command reads it back. 'show health' answers the other question,
by running a probe now and reporting what the daemon is doing at this
moment.";
                ze:help "List the plugins compiled into this binary.";
            }

            container declarations {
                config false;
                ze:command "ze-plugin:show-declarations";
                description "Each row names one plugin, says whether its code is in this
binary or in another one, and carries the commands it serves and the pipe
aliases it puts on them. Add 'config <path>' and the plugins that file
declares gain a row too, external ones included.
A plugin whose declaration could not be read keeps its row and says why in
the state field, so a plugin is never missing from the answer.
'show plugin list' answers the other question, which plugins this binary
carries and what each plugin's own init() recorded.";
                ze:help "Show what each plugin declares about its command surface.";

                container config {
                    config false;
                    ze:command "ze-plugin:show-declarations-config";
                    description "The keyword types the value after it, so the reader of the
command line knows the token is a config file and not a plugin name. The file is
read with the daemon's own loader, so the answer covers the plugins the daemon
would start from it.";
                    ze:help "Read the plugin blocks of a config file as well.";
                    leaf path {
                        type string { length "1..4096"; }
                        mandatory true;
                        description "One filesystem path, or - for a config arriving on stdin. A path
                                     that names no readable file is refused before the read, and a
                                     second path after it is refused.";
                        ze:help "Path of the config file whose plugin blocks are read";
                    }
                }
            }
        }
    }
}
