module ze-plugin-cmd {
    namespace "urn:ze:plugin:cmd";
    prefix plugcmd;
    import ze-extensions { prefix ze; }
    description "show plugins command tree. Owned by internal/component/plugin because the handler reads the internal plugin registry. See ai/rules/plugins.md.";
    revision 2026-08-30 { description "Declare show plugins, the command that replaces the root plugin-listing flag."; }

    container show {
        config false;
        description "Read-only commands to inspect system, protocol, and network state";

        container plugins {
            config false;
            ze:command "ze-show:plugins";
            description "List the plugins compiled into this binary.
Each row carries the plugin name, what it does, the address families it
handles, the RFCs it implements, and the BGP capability codes it owns.";
        }
    }
}
