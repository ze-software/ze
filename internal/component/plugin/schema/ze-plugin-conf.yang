module ze-plugin-conf {
    namespace "urn:ze:plugin:conf";
    prefix plug;

    import ze-types { prefix zt; }
    import ze-extensions { prefix ze; }

    description "Plugin configuration for ZeBGP";

    revision 2026-01-01 {
        description "Initial revision";
    }

    container plugin {
        description "Plugin configuration";

        container hub {
            description "Plugin transport and auth configuration";

            list server {
                key "name";
                ze:listener;
                description "Named hub server instances (TLS listeners)";

                leaf name {
                    type string { length "1..64"; }
                    description "Server block name (e.g., local, central)";
                }

                uses zt:listener;

                leaf secret {
                    type string;
                    ze:sensitive;
                    description "Auth token for plugin connections (min 32 chars)";
                }

                list client {
                    key "name";
                    description "Accepted remote managed clients";

                    leaf name {
                        type string { length "1..64"; }
                        description "Client identity name";
                    }

                    leaf secret {
                        type string;
                        ze:sensitive;
                        description "Per-client auth token (min 32 chars)";
                    }
                }
            }

            list client {
                key "name";
                description "Outbound hub connections (managed client mode)";

                leaf name {
                    type string { length "1..64"; }
                    description "Client identity name";
                }

                leaf host {
                    type string;
                    description "Remote hub address";
                }

                leaf port {
                    type uint16;
                    description "Remote hub port";
                }

                leaf secret {
                    type string;
                    ze:sensitive;
                    description "Auth token (min 32 chars)";
                }
            }
        }

        list internal {
            key "name";
            description "Built-in plugin running in-process";

            leaf name {
                type string {
                    length "1..64";
                }
                description "Plugin name";
            }

            leaf use {
                type string {
                    length "1..64";
                }
                ze:validate "internal-plugin-name";
                description "Name of a built-in plugin to run in-process";
            }
        }

        list external {
            key "name";
            description "External plugin process";

            leaf name {
                type string {
                    length "1..64";
                }
                description "Plugin name";
            }

            leaf run {
                type string;
                description "Command to execute plugin as external process (with args)";
            }

            leaf use {
                type string;
                description "Name of a built-in plugin to run in-process (mutually exclusive with run)";
            }

            leaf encoder {
                type enumeration {
                    enum json { description "JSON encoding"; }
                    enum text { description "Human-readable text encoding"; }
                }
                description "Event encoding format";
            }

            leaf respawn {
                type boolean;
                description "Respawn on exit";
            }

            leaf timeout {
                type string;
                description "Startup timeout (e.g., 10s, 1m)";
            }
        }
    }

}
