module ze-traffic-stat-cmd {
    namespace "urn:ze:traffic-stat:cmd";
    prefix trafficstatcmd;
    import ze-extensions { prefix ze; }
    description "show/monitor traffic stat command tree. Owned by the trafficstat component. Container-merges onto the shared `traffic` namespace.";
    revision 2026-07-13 { description "Nest under show/monitor traffic stat (was traffic-stat), per R9 namespace split."; }
    revision 2026-06-29 { description "Initial: traffic monitoring aggregation service CLI."; }

    container show {
        config false;
        ze:help "Read-only commands to inspect system, protocol, and network state.";

        container traffic {
            config false;
            ze:help "Traffic subsystem: QoS control and byte-usage accounting.";

            container stat {
                config false;
                ze:command "ze-trafficstat:show-traffic-stat";
                description "Without arguments, shows all interfaces. With
'name <interface>', filters to one interface.";
                ze:help "Show aggregated traffic snapshot (interface rates, top talkers, top ports, severity).";
                leaf name {
                    type string;
                    description "The name of one interface, matched exactly against the interface names in
the snapshot. A name in no row leaves the answer empty.";
                    ze:help "Interface name filter";
                }
            }
        }
    }

    container monitor {
        config false;
        ze:help "Continuous monitoring commands (Ctrl-C to stop).";

        container traffic {
            config false;
            description "Monitoring is a live feed and starts empty, so it reports what happens from now on.
                         The accumulated totals are under show traffic.";
            ze:help "Traffic subsystem: QoS control and byte-usage accounting.";

            container stat {
                config false;
                ze:command "ze-trafficstat:monitor-traffic-stat";
                description "Without arguments, shows all interfaces. With
'name <interface>', filters to one interface.";
                ze:help "Start streaming traffic monitor (per-second snapshots).";
                leaf name {
                    type string;
                    description "The name of one interface, matched exactly against the interface names in
each snapshot. Every other interface is left out of the stream.";
                    ze:help "Interface name filter";
                }
            }
        }
    }
}
