module ze-sysctl-conf {
    namespace "urn:ze:sysctl:conf";
    prefix sysctl;

    import ze-types { prefix zt; }
    import ze-extensions { prefix ze; }

    description
        "Sysctl configuration for Ze.
         Generic key/value list for kernel tunables.
         Known keys get type/range validation; unknown keys
         are validated by attempting the write on commit.";

    revision 2026-04-13 {
        description "Initial sysctl plugin schema.";
    }

    container sysctl {
        description "A setting entry applies to the host, and a profile entry applies to the
                     interface units that name the profile. Ze validates a key it knows against the type and the
                     range of that key. Ze accepts a key it does not know, and the kernel then
                     refuses a value it cannot take.";
        ze:help "Kernel tunable management.";

        list setting {
            key "name";
            description "The name uses kernel-native naming, for example net.ipv4.conf.all.forwarding.";
            ze:help "A kernel tunable that Ze sets persistently.";

            leaf name {
                type string;
                description "Ze turns each dot of the key into a path separator and writes the
                             value under /proc/sys. A key under net.ipv4.conf or net.ipv6.conf
                             keeps the dots of the interface name, so eth0.100 reaches
                             net/ipv4/conf/eth0.100. Ze refuses a key that carries two dots in a
                             row.";
                ze:help "Kernel-native sysctl key name.";
            }

            leaf value {
                type string;
                mandatory true;
                description "The leaf is mandatory, so Ze refuses a setting with no value. Ze
                             writes the text into the /proc/sys file of the key. A key Ze knows
                             is checked first: a bool key takes 0 or 1, and a range key takes an
                             integer inside its own bounds.";
                ze:help "Value to set for this key.";
            }
        }

        list profile {
            key "name";
            max-elements 50;
            description "A user-defined profile overrides a built-in profile that has the same name.";
            ze:help "A named collection of kernel tunables that Ze applies together to interface units.";

            leaf name {
                type zt:node-name;
                description "Ze ships five profiles under the names dsr, router, hardened,
                             multihomed and proxy. An entry that carries one of these names
                             replaces that profile for every interface unit. An interface unit
                             names a profile, and Ze then applies the settings of the profile to
                             that unit.";
                ze:help "Profile name (lowercase alphanumeric with hyphens).";
            }

            list setting {
                key "name";
                max-elements 50;
                description "The list holds 50 entries at most. Ze applies these settings to
                             each interface unit that names the profile, and it replaces <iface>
                             in each key with the name of that unit. One profile therefore
                             serves every interface.";
                ze:help "Kernel tunables in this profile.";

                leaf name {
                    type string;
                    description
                        "Ze replaces <iface> with the name of the interface unit the
                         profile is applied to, so one key serves every unit. A key
                         with no placeholder is written once, for the host. The rest
                         of the naming is the same as a top-level setting.";
                    ze:help "Kernel-native sysctl key name.
                             Use <iface> for per-interface keys
                             (substituted at apply time).";
                }

                leaf value {
                    type string;
                    mandatory true;
                    description "The leaf is mandatory, so Ze refuses a profile setting with no
                                 value. Every interface unit that names this profile gets the
                                 same value, because only the key carries the <iface>
                                 placeholder.";
                    ze:help "Value to set for this key.";
                }
            }
        }
    }
}
