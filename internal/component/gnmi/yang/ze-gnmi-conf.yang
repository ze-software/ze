module ze-gnmi-conf {
    namespace "urn:ze:gnmi:conf";
    prefix gnmi;

    import ze-types { prefix zt; }
    import ze-extensions { prefix ze; }

    description "gNMI server configuration for Ze";

    revision 2026-05-28 {
        description "Initial revision";
    }

    container environment {
        description "The environment tree holds the settings of the services Ze runs, beside
the routing configuration rather than inside it.";
        ze:help "Environment settings of the gNMI server.";

        container gnmi {
            description "gNMI is the gRPC Network Management Interface. The Ze gNMI server
answers Get, Set, Subscribe and Capabilities over gRPC.";
            ze:help "Settings of the gNMI server.";

            leaf enabled {
                type boolean;
                default false;
                description "The default is false, so Ze opens no gNMI listener until this
leaf is true.";
                ze:help "Start the gNMI server.";
            }

            leaf token {
                type string;
                ze:sensitive;
                description "Ze hashes the token with sha256 and compares the hash through
subtle.ConstantTimeCompare, so the comparison takes constant time. An empty token
means that the gNMI server does no authentication.";
                ze:help "Bearer token that authenticates a gNMI client.";
            }

            container tls {
                description "The container holds the certificate file and the private-key file
that the gRPC transport presents to a client.";
                ze:help "TLS certificate of the gNMI gRPC transport.";

                leaf cert {
                    type string;
                    description "The file CAN hold one certificate or a chain of them.";
                    ze:help "Path to the PEM-encoded certificate file.";
                }

                leaf key {
                    type string;
                    ze:sensitive;
                    description "The key belongs to the certificate that the cert leaf names.";
                    ze:help "Path to the PEM-encoded private-key file.";
                }
            }

            list server {
                key "name";
                ze:listener;
                description "Each entry binds one address and one port. The address defaults
to 0.0.0.0 and the port defaults to 9339.";
                ze:help "Listen endpoints of the gNMI server.";

                leaf name {
                    type string;
                    description "The name is the list key, and it identifies the entry in the
configuration and in the log.";
                    ze:help "Name of this server instance.";
                }

                uses zt:listener {
                    refine ip {
                        default "0.0.0.0";
                    }
                    refine port {
                        default 9339;
                    }
                }
            }
        }
    }
}
