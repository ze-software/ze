module ze-gnmi-cmd {
    namespace "urn:ze:gnmi:cmd";
    prefix gnmicmd;
    import ze-extensions    { prefix ze; }
    import ze-cli-show-cmd  { prefix clishowcmd; }
    description "gNMI show command: server status and configuration.
         Relocated from the central show schema for plugin self-containment.";
    revision 2026-06-03 { description "Initial revision: relocated from ze-cli-show-cmd."; }

    augment "/clishowcmd:show" {
        container gnmi {
            config false;
            ze:command "ze-show:gnmi";
            description "Show whether the gNMI server is running and how it is configured.
Returns listen address, TLS details, authentication mode, and the
number of active streaming subscribers.";
        }
    }
}
