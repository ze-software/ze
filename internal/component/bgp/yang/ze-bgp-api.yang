module ze-bgp-api {
    namespace "urn:ze:bgp:api";
    prefix bgpapi;

    import ze-extensions { prefix ze; }
    import ze-types { prefix zt; }

    description
        "BGP API operations for Ze.
         RPCs for peer management, route operations, cache control,
         and event subscriptions. Notifications for BGP events.";

    // peer-add and the delete verb's bgp-peer were two spellings of one
    // lifecycle; ze-bgp:peer-create and ze-bgp:peer-delete name the pair.
    revision 2026-10-21 {
        description "Declare rib-clear-advertised, the Adj-RIB-Out withdrawal; declare bgp-health, moved from ze-cli-show-api; declare peer-disable and peer-enable, the administrative hold; declare peer-notify, a NOTIFICATION of any code and subcode, with its Data field as text or as hex octets.";
    }

    revision 2026-10-09 {
        description "Rename peer-add to peer-create; declare peer-delete, moved from ze-cli-delete-api.";
    }

    // peer-save was declared in ze-bgp-cmd-peer-api.yang, which published it as
    // ze-bgp-cmd-peer:peer-save while the handler answers ze-bgp:peer-save.
    revision 2026-10-08 {
        description "Declare peer-save, moved from ze-bgp-cmd-peer-api.";
    }

    revision 2026-02-01 {
        description "Initial revision.";
    }

    // Introspection

    rpc help {
        description "The answer holds one entry for each builtin command, and each entry joins the
command name to its summary with a hyphen. A plugin's own command sits in the
command registry and not in the builtin table, so command-help is the RPC that
reaches it.";
        ze:help "List BGP subcommands.";
        output {
            leaf-list subcommands {
                type string;
                description "One entry for each builtin command. Each entry joins the command name to its
summary with a hyphen. A plugin command is not in the list.";
                ze:help "Available subcommands";
            }
        }
    }

    rpc command-list {
        description "Each row carries the command name and its one-line summary. Give the 'verbose'
argument and each row also carries its source, which is 'builtin'. The rows come
from the dispatcher's builtin table.";
        ze:help "List BGP commands.";
        output {
            list command {
                description "Each row carries the command name and its summary, and with the 'verbose'
argument its source too.";
                ze:help "One row for each builtin command.";
                uses zt:command-info;
            }
        }
    }

    rpc command-help {
        description "The answer carries the one-line summary under 'short-help' and the long
explanation under 'description'. Neither text is derived from the other. The
lookup reads the builtin table first and the plugin command registry after it.";
        ze:help "Show BGP command details.";
        input {
            leaf name {
                type string;
                mandatory true;
                description "The full name of the command the answer describes. The lookup reads the
builtin table first and the plugin command registry after it.";
                ze:help "Command name";
            }
        }
        output {
            leaf help {
                type string;
                description "The long explanation of the named command, as its author registered it. The
one-line summary is answered beside it under 'short-help'.";
                ze:help "Detailed help text";
            }
        }
    }

    rpc command-complete {
        description "The match is a case-insensitive prefix over the builtin command names. Each
candidate carries its summary beside the name. A prefix that matches nothing
answers an empty list and not an error.";
        ze:help "Complete BGP command/args.";
        input {
            leaf partial {
                type string;
                mandatory true;
                description "The start of a command name. The match is a case-insensitive prefix over the
builtin command names.";
                ze:help "Partial command string";
            }
        }
        output {
            leaf-list completions {
                type string;
                description "One candidate for each builtin command whose name starts with the partial
string, with its summary beside the name. The list is empty when nothing matches.";
                ze:help "Completion candidates";
            }
        }
    }

    // Plugin configuration

    rpc plugin-encoding {
        description "The mode governs the events this plugin process receives. 'json' is the default.
The daemon holds the mode on the calling process, so it changes nothing for
another plugin.";
        ze:help "Set event encoding (json|text).";
        input {
            leaf encoding {
                type zt:encoding-mode;
                mandatory true;
                description "The encoding of every event the daemon sends to the calling plugin process.
The value takes effect for that process alone.";
                ze:help "Encoding format";
            }
        }
    }

    rpc plugin-format {
        description "The format governs how the BGP wire bytes are rendered inside each event.
'parsed' carries the decoded fields alone and is the default. 'hex' and 'base64'
carry the wire bytes in that encoding. 'full' carries the decoded fields and the
wire bytes together.";
        ze:help "Set wire format (hex|base64|parsed|full).";
        input {
            leaf format {
                type zt:wire-format;
                mandatory true;
                description "How the BGP wire bytes are rendered inside each event the calling process
receives. 'parsed' is the default, and 'full' is the only value that carries the decoded
fields and the bytes together.";
                ze:help "Wire format";
            }
        }
    }

    rpc plugin-ack {
        description "'sync' makes an announce or a withdraw wait for wire transmission before the
daemon answers the ACK. 'async' answers as soon as the command is accepted, and
it is the default. The daemon holds the mode on the calling process.";
        ze:help "Set ACK timing (sync|async).";
        input {
            leaf mode {
                type zt:ack-mode;
                mandatory true;
                description "'sync' delays the ACK of an announce or a withdraw until the bytes are on the
wire. 'async' answers when the command is accepted and is the default.";
                ze:help "ACK mode";
            }
        }
    }

    // Peer operations

    rpc peer-list {
        description "Each row carries the peer address, its name, and its peer-group. The remote and
local ASN, the local bind address, the FSM state and the router ID follow. The
receive hold time, the send hold time, the connect retry interval, and the
seconds since the session became established close the row.";
        ze:help "List configured peers.";
        input {
            leaf selector {
                type zt:peer-selector;
                description "A peer address, a peer name, '*', or a comma-separated list of them. With no
selector every configured peer is listed.";
                ze:help "Peer filter";
            }
        }
        output {
            list peer {
                description "The rows carry the peer-info fields: address, name, group, both ASNs, FSM
state, router ID, the three timers and the uptime.";
                ze:help "One row for each peer the selector matched.";
                uses zt:peer-info;
            }
        }
    }

    rpc peer-show {
        description "The rows carry the same peer-info fields peer-list answers. Those are the
address, the name, the group, the two ASNs, the FSM state, the router ID, the
three timers, and the uptime. The selector is optional here, as it is for
peer-list.";
        ze:help "Show detailed peer information.";
        input {
            leaf selector {
                type zt:peer-selector;
                description "A peer address, a peer name, '*', or a comma-separated list of them. With no
selector every configured peer is shown.";
                ze:help "Peer filter";
            }
        }
        output {
            list peer {
                description "The rows carry the same peer-info fields peer-list answers, so the two RPCs
differ in their summary and not in their shape.";
                ze:help "One row for each peer the selector matched.";
                uses zt:peer-info;
            }
        }
    }

    rpc overview {
        description "The answer opens with the daemon uptime, the count of configured peers, and the
count of peers in the Established state. The peer rows follow. A first argument
that names neither a subcommand nor an address family is refused.";
        ze:help "Show the BGP overview (peer table with statistics).";
        output {
            leaf uptime {
                type string;
                description "The time since the daemon started, truncated to whole seconds and written as a
Go duration such as '1h2m3s'.";
                ze:help "Daemon uptime";
            }
            leaf peers-configured {
                type uint32;
                description "The number of peers in the running configuration, whatever FSM state each one
is in.";
                ze:help "Total configured peers";
            }
            leaf peers-established {
                type uint32;
                description "The number of configured peers whose FSM is in the Established state at the
time of the answer.";
                ze:help "Peers in Established state";
            }
            list peer {
                description "The rows follow the three aggregate leaves as their sibling, so a display
filter selects them by key. Each row carries the peer-info fields.";
                ze:help "One row for each configured peer.";
                uses zt:peer-info;
            }
        }
    }

    rpc peer-show-capabilities {
        description "The answer carries the peer address, the FSM state, and a boolean that is true
once the OPEN exchange completed. The selector is mandatory, so this RPC reads
one peer and never every peer.";
        ze:help "Show negotiated capabilities for peer.";
        input {
            leaf selector {
                type zt:peer-selector;
                mandatory true;
                description "A peer address, a peer name, or a comma-separated list of them. The selector
is mandatory, so no request reads every peer by default.";
                ze:help "Peer filter";
            }
        }
        output {
            leaf peer {
                type zt:ip-address;
                description "The IP address of the peer the capabilities belong to.";
                ze:help "Peer address";
            }
            leaf state {
                type string;
                description "The name of the FSM state the session is in at the time of the answer.";
                ze:help "FSM state";
            }
            leaf negotiation-complete {
                type boolean;
                description "True once both OPEN messages were exchanged and the capabilities are known.
While it is false the negotiated families and the add-path fields are absent.";
                ze:help "True if OPEN exchange completed";
            }
        }
    }

    rpc peer-show-statistics {
        description "The answer carries the peer address, its ASN, the FSM state, and the session
uptime. Six counters follow, for UPDATE, KEEPALIVE and End-of-RIB messages in
each direction. Four rate fields give the UPDATE and KEEPALIVE traffic per
second.";
        ze:help "Show per-peer update statistics with rates.";
        input {
            leaf selector {
                type zt:peer-selector;
                description "A peer address, a peer name, '*', or a comma-separated list of them. A
selector that matches no peer is refused.";
                ze:help "Peer filter";
            }
        }
        output {
            leaf address {
                type zt:ip-address;
                description "The IP address of the peer this row describes.";
                ze:help "Peer address";
            }
            leaf remote-as {
                type zt:asn-notated;
                description "The AS number of the peer. Its notation is the one the bgp/as-notation leaf
selects, asplain or asdot.";
                ze:help "Peer ASN, in the notation bgp/as-notation selects";
            }
            leaf state {
                type string;
                description "The name of the FSM state the session is in at the time of the answer.";
                ze:help "FSM state";
            }
            leaf uptime {
                type string;
                description "The time since the session became Established, truncated to whole seconds
and written as a Go duration such as '5m3s'. It is zero while the session is not
Established.";
                ze:help "Session uptime";
            }
            leaf updates-received {
                type uint32;
                description "The count of UPDATE messages received from the peer. rate-updates-received
divides it by the uptime.";
                ze:help "UPDATE messages received";
            }
            leaf updates-sent {
                type uint32;
                description "The count of UPDATE messages sent to the peer. rate-updates-sent divides it
by the uptime.";
                ze:help "UPDATE messages sent";
            }
            leaf keepalives-received {
                type uint32;
                description "The count of KEEPALIVE messages received from the peer.
rate-keepalives-received divides it by the uptime.";
                ze:help "KEEPALIVE messages received";
            }
            leaf keepalives-sent {
                type uint32;
                description "The count of KEEPALIVE messages sent to the peer. rate-keepalives-sent
divides it by the uptime.";
                ze:help "KEEPALIVE messages sent";
            }
            leaf eor-received {
                type uint32;
                description "The count of End-of-RIB markers received from the peer, one for each address
family whose initial table the peer finished sending.";
                ze:help "End-of-RIB markers received";
            }
            leaf eor-sent {
                type uint32;
                description "The count of End-of-RIB markers sent to the peer, one for each address family
whose initial table Ze finished sending.";
                ze:help "End-of-RIB markers sent";
            }
            leaf rate-updates-received {
                type string;
                description "The updates-received count divided by the uptime in seconds, as a decimal
number. It is 0 while the uptime is zero.";
                ze:help "Updates received per second";
            }
            leaf rate-updates-sent {
                type string;
                description "The updates-sent count divided by the uptime in seconds, as a decimal number.
It is 0 while the uptime is zero.";
                ze:help "Updates sent per second";
            }
            leaf rate-keepalives-received {
                type string;
                description "The keepalives-received count divided by the uptime in seconds, as a decimal
number. It is 0 while the uptime is zero.";
                ze:help "Keepalives received per second";
            }
            leaf rate-keepalives-sent {
                type string;
                description "The keepalives-sent count divided by the uptime in seconds, as a decimal
number. It is 0 while the uptime is zero.";
                ze:help "Keepalives sent per second";
            }
        }
    }

    rpc peer-clear-soft {
        description "The soft clear sends one ROUTE-REFRESH for each family the session negotiated,
so the peer re-advertises its routes and the session stays up. RFC 2918 Section
4 permits the message only after the peer sent the Route Refresh Capability. The
selector resolves to one peer, and a wildcard is refused. The answer lists the
families that were refreshed.";
        ze:help "Soft-clear peer (send ROUTE-REFRESH per negotiated family).";
        input {
            leaf selector {
                type zt:peer-selector;
                mandatory true;
                description "A peer address or a peer name that resolves to one peer. A wildcard is
refused.";
                ze:help "Peer address";
            }
        }
        output {
            leaf peer {
                type zt:ip-address;
                description "The IP address of the peer that received the ROUTE-REFRESH messages.";
                ze:help "Peer address";
            }
            leaf action {
                type string;
                description "The constant text 'soft-clear'. A caller reading a mixed stream of answers
uses it to tell which operation produced this one.";
                ze:help "Always soft-clear";
            }
            leaf-list families-refreshed {
                type zt:address-family;
                description "One entry for each negotiated address family a ROUTE-REFRESH was sent for.";
                ze:help "Families refreshed";
            }
        }
    }

    rpc peer-create {
        description "The address and the ASN are required, and every other input is optional.
'local-as' overrides the local ASN and 'router-id' overrides the router ID.
'receive-hold-time' is the hold time RFC 4271 defines. 'send-hold-time' is the
send hold timer RFC 9687 defines, where 0 selects the automatic value. 'connect'
and 'accept' each default to true, so the peer dials the address and answers a
connection from it. 'family' names the address families the OPEN offers, and
with no 'family' the OPEN carries no multiprotocol capability. 'attach' names
the plugin processes this peer feeds. The peer lives in the running daemon and
the running configuration, and nothing is written to the configuration file. A
commit or a reload whose configuration does not declare the peer keeps it
running; 'delete bgp peer' is how it leaves, and 'ze-bgp:peer-save' is what
writes it to the file. 'create bgp peer <address> asn <asn>' is the CLI path.";
        ze:help "Create a peer in the running daemon.";
        input {
            leaf address {
                type zt:ip-address;
                mandatory true;
                description "The IPv4 or IPv6 address of the peer. It is the key of the peer, and
'delete bgp peer' accepts the same address.";
                ze:help "Peer address";
            }
            leaf asn {
                type zt:asn-notated;
                mandatory true;
                description "The AS number the peer announces in its OPEN, 1 to 4294967295. Ze stores the
decimal form whichever notation was given.";
                ze:help "Peer ASN, in any notation RFC 5396 names";
            }
            leaf local-as {
                type zt:asn-notated;
                description "The AS number Ze announces in its own OPEN to this peer, 1 to 4294967295.
Without it the daemon's local AS applies.";
                ze:help "Local ASN override, in any notation RFC 5396 names";
            }
            leaf local-address {
                type zt:ip-address;
                description "The IPv4 or IPv6 address of this host that the TCP connection to the peer is
bound to.";
                ze:help "Local bind address";
            }
            leaf router-id {
                type zt:ipv4-address;
                description "The BGP Identifier Ze sends in its OPEN to this peer, as a dotted quad.
0.0.0.0 is refused, and without it the daemon's router ID applies.";
                ze:help "Router ID override";
            }
            leaf receive-hold-time {
                type uint16;
                description "The Hold Time in seconds that Ze proposes in its OPEN to this peer, 0 to
65535.";
                ze:help "Receive hold time (RFC 4271)";
            }
            leaf send-hold-time {
                type uint16;
                description "The send hold time in seconds, 0 to 65535. A value of 0 lets Ze derive it.";
                ze:help "Send hold time (RFC 9687, 0=auto)";
            }
            leaf connect-retry {
                type uint16;
                description "The seconds Ze waits between two connection attempts to the peer, 0 to
65535.";
                ze:help "Connect retry interval";
            }
            leaf connect {
                type boolean;
                description "When true Ze dials the peer address. Set it false when the peer opens the
connection.";
                ze:help "Dial the peer (default true)";
            }
            leaf accept {
                type boolean;
                description "When true Ze answers a TCP connection the peer opens. Set it false when Ze
alone dials.";
                ze:help "Answer a connection from the peer (default true)";
            }
            leaf-list family {
                type zt:address-family;
                description "An address family the OPEN offers in its multiprotocol capability. A name no
family registry entry matches is refused.";
                ze:help "Address family to negotiate";
            }
            leaf graceful-restart {
                type uint16;
                description "The Restart Time in seconds Ze advertises in its Graceful Restart capability,
0 to 4095, which is the width of the field.";
                ze:help "Restart Time in seconds (RFC 4724)";
            }
            leaf group-updates {
                type boolean;
                description "When true this peer's UPDATEs are grouped with those of other peers that
carry the same attributes. When false they are built for this peer alone.";
                ze:help "Group this peer's UPDATEs with other peers (default true)";
            }
            leaf-list attach {
                type zt:node-name;
                description "The name of a plugin process that receives every message from this peer and
can send every message type to it. Give one entry per process.";
                ze:help "Plugin process this peer feeds";
            }
        }
        output {
            leaf peer {
                type zt:ip-address;
                description "The IP address of the peer that was created, as the input gave it.";
                ze:help "Address of the peer created";
            }
            leaf remote-as {
                type zt:asn-notated;
                description "The AS number of the created peer. Its notation is the one the bgp/as-notation
leaf selects, asplain or asdot.";
                ze:help "Remote AS of the peer created, in the notation bgp/as-notation selects";
            }
            leaf message {
                type string;
                description "The constant text 'peer created'. It confirms the peer exists in the running
daemon and not in the configuration file.";
                ze:help "Always 'peer created'";
            }
        }
    }

    rpc peer-delete {
        description "The selector is a peer address or a configured peer name, and the
wildcard is refused. Ze stops the TCP session and removes the peer from the
running daemon. The configuration file on disk does not change, so a peer the
file declares comes back on a reload until 'ze-bgp:peer-save' takes it out.";
        ze:help "Delete a peer from the running daemon.";
    }

    rpc peer-save {
        description "The method takes no argument and acts on the whole running peer
set. It reconciles the configuration file to that set in both directions: a
peer created through 'ze-bgp:peer-create' is written into the file, and a peer the
file declares that 'ze-bgp:peer-delete' removed is taken out of it. A peer both
sides hold is not rewritten. Nothing about the running daemon changes. The
answer carries 'added', 'removed' and 'config', which names the file. An
argument is refused, because after a removal no peer is left for a selector to
name.";
        ze:help "Write the running peer set to the configuration file.";
    }

    rpc peer-teardown {
        description "The subcode is the NOTIFICATION subcode for error code 6 and it takes 0 to 255.
Ze sends an RFC 8203 shutdown communication message with subcode 2,
administrative shutdown, and with subcode 4, administrative reset, and with no
other subcode. The message is truncated to the length the wire carries, and the
answer echoes the truncated text.";
        ze:help "Teardown peer session with CEASE notification.";
        input {
            leaf selector {
                type zt:peer-selector;
                mandatory true;
                description "A peer address, a peer name, or a comma-separated list of them. Every matched
session receives the NOTIFICATION, and the peer stays configured.";
                ze:help "Peer filter";
            }
            leaf subcode {
                type uint8;
                description "The Cease subcode, 0 to 255, that the NOTIFICATION carries under error code
6. Subcodes 2 and 4 can carry a shutdown communication message.";
                ze:help "CEASE subcode";
            }
        }
    }

    rpc peer-notify {
        description "Ze closes the session with a NOTIFICATION carrying the given error code and
error subcode, any value an octet holds. Under Cease (6), subcode 2 or 4, the
text is the RFC 9003 Shutdown Communication; under every other pair it is the
Data field. Both are sent as UTF-8. With no text the Data field is empty. A
text that does not fit is refused and the session stays up: more than 128
octets under Cease 2 or 4 (RFC 9003 Section 3), more than 4075 octets
otherwise, or text that is not UTF-8. The hex leaf, given in place of the text,
is the Data field itself, sent octet for octet and refused over 4075 octets.
The answer echoes the Data field in hex.";
        ze:help "Close a peer session with a NOTIFICATION of any code and subcode.";
        input {
            leaf selector {
                type zt:peer-selector;
                mandatory true;
                description "A peer address or a peer name. A selector that matches more than one peer is
refused.";
                ze:help "Peer filter";
            }
            leaf code {
                type uint8;
                mandatory true;
                description "The NOTIFICATION error code, 0 to 255 (RFC 4271 Section 4.5).";
                ze:help "NOTIFICATION error code";
            }
            leaf subcode {
                type uint8;
                mandatory true;
                description "The NOTIFICATION error subcode, 0 to 255.";
                ze:help "NOTIFICATION error subcode";
            }
            leaf hex {
                type string;
                description "The Data field in hexadecimal, two digits for each octet, given in place of
the text. It is sent as it is, with no encoding. More than 4075 octets, an odd
number of digits, or a character other than 0-9, a-f or A-F is refused.";
                ze:help "Data field octets in hexadecimal";
            }
            leaf text {
                type string;
                description "The Data field text: every word after the subcode, joined by one space.";
                ze:help "Data field text";
            }
        }
    }

    rpc peer-disable {
        description "Ze holds the peer administratively down. A running session is closed with a
Cease NOTIFICATION, subcode 2 (Administrative Shutdown), carrying the message as
its RFC 9003 Shutdown Communication, truncated to the 255 octets the wire
carries. A peer with no session is held all the same: Ze opens no session and
answers an inbound connection with Cease subcode 5 (Connection Rejected), until
peer-enable. The routes queued for the peer are kept and sent once it is enabled.";
        ze:help "Hold a peer administratively down.";
        input {
            leaf selector {
                type zt:peer-selector;
                mandatory true;
                description "A peer address or a peer name. A selector that matches more than one peer is
refused.";
                ze:help "Peer filter";
            }
            leaf message {
                type string;
                description "The RFC 9003 Shutdown Communication. Absent, the Cease carries none.";
                ze:help "Shutdown communication";
            }
        }
    }

    rpc peer-enable {
        description "Ze releases the administrative hold of peer-disable or of the peer shutdown
container, and the peer connects straight away. A peer that is not held is left
as it is. The release lasts until a commit adds or removes the shutdown
container.";
        ze:help "Release a peer's administrative hold.";
        input {
            leaf selector {
                type zt:peer-selector;
                mandatory true;
                description "A peer address or a peer name. A selector that matches more than one peer is
refused.";
                ze:help "Peer filter";
            }
        }
    }

    rpc rib-clear-advertised {
        description "Withdraws every route the selected peers' current sessions hold in their
Adj-RIB-Out, configured routes included, and forgets the peers' configured route
set so a reload sends it again. RFC 4271 Section 9.2 sends each withdrawal as an
UPDATE. A selector that matches no peer is refused.";
        ze:help "Withdraw the Adj-RIB-Out of the selected peers.";
        input {
            leaf selector {
                type zt:peer-selector;
                mandatory true;
                description "A peer address, a peer name, an AS pattern, a comma-separated list of them, or
'*' for every peer.";
                ze:help "Peer filter (* for all)";
            }
            leaf family {
                type zt:address-family;
                description "The one address family to withdraw. Absent, every family is withdrawn.";
                ze:help "Address family";
            }
        }
        output {
            leaf withdrawn {
                type uint32;
                description "The count of routes withdrawn, summed over the selected peers.";
            }
        }
    }

    rpc peer-flush {
        description "The RPC returns once the forward pool has drained, so a test asserts on what the
peer received without a fixed sleep. A selector of '*', or no selector at all,
flushes every peer. The wait is bounded at 30 seconds.";
        ze:help "Wait for forward pool to drain (barrier).";
        input {
            leaf selector {
                type zt:peer-selector;
                mandatory true;
                description "A peer address, a peer name, or '*'. '*' drains the forward pool of every
peer, and a name that resolves to no peer is refused.";
                ze:help "Peer filter (* for all)";
            }
        }
        output {
            leaf peer {
                type string;
                description "What the barrier drained: the address of the one peer, or '*' when every
peer was flushed.";
                ze:help "Peer selector that was flushed";
            }
            leaf action {
                type string;
                description "The constant text 'flush'. A caller reading a mixed stream of answers uses it
to tell which operation produced this one.";
                ze:help "Always flush";
            }
        }
    }

    // Route operations

    rpc peer-update {
        description "The encoding chooses the parser. 'text' reads the route DSL. 'hex' and 'b64'
read encoded UPDATE bytes. 'cursor' reads a saved position. The text form
carries announce, withdraw and End-of-RIB in one command, and the answer counts
the NLRIs each way.";
        ze:help "Batch UPDATE with text/hex/b64 encoding.";
        input {
            leaf peer-selector {
                type zt:peer-selector;
                mandatory true;
                description "The peers the UPDATE goes to, as a peer address, a peer name, '*', or a
comma-separated list of them.";
                ze:help "Target peers";
            }
            leaf encoding {
                type zt:encoding-mode;
                mandatory true;
                description "The parser the command goes to: 'text' for the route DSL, 'hex' or 'b64' for
encoded UPDATE bytes.";
                ze:help "Command encoding";
            }
            leaf command {
                type string;
                mandatory true;
                description "The route DSL text, or the encoded UPDATE bytes when the encoding is hex or
b64. One text command can announce, withdraw and send End-of-RIB together.";
                ze:help "Route DSL command";
            }
        }
        output {
            leaf announced {
                type uint32;
                description "The number of NLRIs the command announced. It counts NLRIs and not UPDATE
messages.";
                ze:help "Number of NLRIs announced";
            }
            leaf withdrawn {
                type uint32;
                description "The number of NLRIs the command withdrew. It counts NLRIs and not UPDATE
messages.";
                ze:help "Number of NLRIs withdrawn";
            }
        }
    }

    // Route refresh (RFC 7313)

    rpc peer-borr {
        description "RFC 7313 Section 4 requires a BoRR message before the speaker starts a route
refresh. That holds for a local refresh and for one that answers a request from
the peer. The family names which Adj-RIB-Out the re-advertisement covers. Send
peer-eorr once that re-advertisement is complete.";
        ze:help "Send Beginning of Route Refresh.";
        input {
            leaf peer-selector {
                type zt:peer-selector;
                mandatory true;
                description "The peers that receive the BoRR message, as a peer address, a peer name, '*',
or a comma-separated list of them.";
                ze:help "Target peers";
            }
            leaf family {
                type zt:address-family;
                mandatory true;
                description "The address family the BoRR names. It is the Adj-RIB-Out the re-advertisement
that follows covers.";
                ze:help "Address family";
            }
        }
    }

    rpc peer-eorr {
        description "RFC 7313 Section 4: 'After the speaker completes the re-advertisement of the
entire Adj-RIB-Out to the peer, it MUST send an EoRR message.' The family MUST
be the one peer-borr opened. RFC 7313 Section 4 applies the procedure only after
the peer sent the Enhanced Route Refresh Capability.";
        ze:help "Send End of Route Refresh.";
        input {
            leaf peer-selector {
                type zt:peer-selector;
                mandatory true;
                description "The peers that receive the EoRR message, as a peer address, a peer name, '*',
or a comma-separated list of them.";
                ze:help "Target peers";
            }
            leaf family {
                type zt:address-family;
                mandatory true;
                description "The address family the EoRR closes. It MUST be the family the matching
peer-borr opened.";
                ze:help "Address family";
            }
        }
    }

    // Raw message

    rpc peer-raw {
        description "With a message type keyword, Ze builds the BGP header and the data carries the
payload alone. Without one, the data MUST carry the marker and the header too.
The types are open, update, notification, keepalive and route-refresh, and the
encodings are hex and b64. Nothing validates the bytes, so this RPC can put a
malformed message on the wire.";
        ze:help "Send raw bytes to peer (no validation).";
        input {
            leaf peer-selector {
                type zt:peer-selector;
                mandatory true;
                description "The peers the bytes go to, as a peer address, a peer name, '*', or a
comma-separated list of them.";
                ze:help "Target peers";
            }
            leaf type {
                type string;
                description "One of open, update, notification, keepalive and route-refresh. With a type
Ze writes the marker and the header, and the data carries the payload alone.";
                ze:help "Message type hint";
            }
            leaf encoding {
                type zt:encoding-mode;
                mandatory true;
                description "The encoding the data leaf is written in, hex or b64.";
                ze:help "Data encoding";
            }
            leaf data {
                type string;
                mandatory true;
                description "The message bytes in the named encoding. Without a type they carry the marker,
the length and the type too, and nothing checks them.";
                ze:help "Raw data";
            }
        }
    }

    // Cache operations

    rpc cache {
        description "The action is one of list, retain, release, expire and forward. Every action
except list takes a message ID. 'forward' takes a peer selector as well. A
message ID field holding a comma-separated list runs the action over each ID in
one call.";
        ze:help "BGP message cache operations.";
        input {
            leaf action {
                type string;
                mandatory true;
                description "One of list, retain, release, expire and forward. Every action except list
needs a message-id, and another word is refused.";
                ze:help "Cache action (list|retain|release|expire|forward)";
            }
            leaf message-id {
                type uint64;
                description "The ID of a cached message, as the list action answers it. A comma-separated
list of IDs runs the action once for each ID.";
                ze:help "Cache message ID";
            }
            leaf peer-selector {
                type zt:peer-selector;
                description "The peers a forwarded UPDATE goes to, as a peer address, a peer name, '*', or
a comma-separated list of them. Only the forward action reads it.";
                ze:help "Target peers (for forward)";
            }
        }
    }

    // Commit operations

    rpc commit {
        description "The actions are start, end, eor, rollback, show, withdraw and list. Each one
except list takes a name. 'withdraw' takes a route prefix after the name. 'list'
answers the open commit names and their count.";
        ze:help "Named commit operations.";
        input {
            leaf name {
                type string;
                description "The name of the commit the action operates on. Every action except list needs
it, and start is what first creates the name.";
                ze:help "Commit name";
            }
        }
    }

    // Subscription

    rpc subscribe {
        description "An operator who types this at a running daemon creates a runtime override. The
event is delivered whether or not the peer's configuration grants the type, and
the next configuration apply discards the override. The configuration document
stays the durable statement of what the daemon feeds.";
        ze:help "Subscribe to BGP events (streaming).";
        input {
            leaf-list events {
                type string;
                description "An event type name, as event-list answers it. Each name adds one runtime
subscription for the calling process.";
                ze:help "Event types to subscribe to";
            }
        }
    }

    rpc unsubscribe {
        description "The answer carries 'removed', which is false when the process held no matching
subscription. The namespace and the event type are echoed back, so a caller sees
which subscription the arguments resolved to.";
        ze:help "Unsubscribe from BGP events.";
    }

    rpc event-list {
        description "The answer holds the event type names registered in the BGP namespace, each with
its description. subscribe takes its event names from that same registry.";
        ze:help "List available event types.";
        output {
            list event {
                description "Each row carries the name subscribe takes and the one-line text the
event registry holds beside it, in registry order.";
                ze:help "One row for each event type registered in the BGP namespace.";
                uses zt:event-type-info;
            }
        }
    }

    // Notifications

    notification peer-state-change {
        ze:method "ze-bgp:peer-state-change";
        description "Both states are FSM state names. No producer emits this notification today, so a
subscriber that waits for it receives nothing.";
        ze:help "Peer FSM state changed.";
        leaf address {
            type zt:ip-address;
            description "The IP address of the peer whose FSM moved.";
            ze:help "Peer address";
        }
        leaf old-state {
            type string;
            description "The name of the FSM state the peer left.";
            ze:help "Previous FSM state";
        }
        leaf new-state {
            type string;
            description "The name of the FSM state the peer entered.";
            ze:help "New FSM state";
        }
    }

    notification route-received {
        ze:method "ze-bgp:route-received";
        description "One notification describes one UPDATE message. No producer emits this notification
today, so a subscriber that waits for it receives nothing.";
        ze:help "BGP UPDATE received from peer.";
        leaf peer {
            type zt:ip-address;
            description "The IP address of the peer that sent the UPDATE.";
            ze:help "Source peer";
        }
        leaf family {
            type zt:address-family;
            description "The address family of the NLRIs the UPDATE carried.";
            ze:help "Address family";
        }
        leaf count {
            type uint32;
            description "The number of NLRIs the UPDATE carried.";
            ze:help "Number of NLRI in update";
        }
    }

    notification route-update-sent {
        ze:method "ze-bgp:route-update-sent";
        description "The notification names the peer and the family and carries no NLRI count. No
producer emits this notification today, so a subscriber that waits for it receives nothing.";
        ze:help "BGP UPDATE sent to peer.";
        leaf peer {
            type zt:ip-address;
            description "The IP address of the peer the UPDATE went to.";
            ze:help "Target peer";
        }
        leaf family {
            type zt:address-family;
            description "The address family of the NLRIs the UPDATE carried.";
            ze:help "Address family";
        }
    }

    notification eor-received {
        ze:method "ze-bgp:eor-received";
        description "One End-of-RIB marker closes the initial table of one address family. No producer
emits this notification today, so a subscriber that waits for it receives nothing.";
        ze:help "End-of-RIB marker received.";
        leaf peer {
            type zt:ip-address;
            description "The IP address of the peer that sent the End-of-RIB marker.";
            ze:help "Source peer";
        }
        leaf family {
            type zt:address-family;
            description "The address family whose initial table the marker closes.";
            ze:help "Address family";
        }
    }

    notification graceful-restart-state {
        ze:method "ze-bgp:graceful-restart-state";
        description "The state is a string and no enumeration constrains it. No producer emits this
notification today, so a subscriber that waits for it receives nothing.";
        ze:help "Graceful restart state changed.";
        leaf peer {
            type zt:ip-address;
            description "The IP address of the peer whose graceful restart state changed.";
            ze:help "Peer address";
        }
        leaf state {
            type string;
            description "The graceful restart state the peer entered, as free text.";
            ze:help "GR state";
        }
    }

    notification session-established {
        ze:method "ze-bgp:session-established";
        description "The peer address and its AS number identify the session. No producer emits this
notification today, so a subscriber that waits for it receives nothing.";
        ze:help "BGP session established.";
        leaf peer {
            type zt:ip-address;
            description "The IP address of the peer the session was established with.";
            ze:help "Peer address";
        }
        leaf asn {
            type zt:asn;
            description "The AS number the peer announced in its OPEN, as a plain decimal integer.";
            ze:help "Peer ASN, as a decimal value";
        }
    }

    notification session-closed {
        ze:method "ze-bgp:session-closed";
        description "The reason is free text and no enumeration constrains it. No producer emits this
notification today, so a subscriber that waits for it receives nothing.";
        ze:help "BGP session closed.";
        leaf peer {
            type zt:ip-address;
            description "The IP address of the peer whose session closed.";
            ze:help "Peer address";
        }
        leaf reason {
            type string;
            description "A text stating why the session closed.";
            ze:help "Close reason";
        }
    }

    // show bgp health (ze-bgp:show-health) points at this rpc from
    // ze-peer-cmd; the handler is bgp/plugins/cmd/peer/health.go.
    rpc bgp-health {
        description "Each row carries the peer address, the state, the remote AS and
the uptime. Beside the rows, count holds the peer total and not-established
holds how many are down. The answer renders as a table, so '| match Idle |
count' answers how many peers are not established.";
        ze:help "Show BGP peer health sorted by state and activity.";
    }
}
