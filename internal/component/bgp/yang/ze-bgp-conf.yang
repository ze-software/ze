module ze-bgp-conf {
    namespace "urn:ze:bgp:conf";
    prefix bgp;

    import ze-types { prefix zt; }
    import ze-extensions { prefix ze; }
    import ze-hub-conf { prefix hub; }

    description "BGP configuration for ZeBGP";

    revision 2026-10-21 {
        description "Add the peer shutdown container: the peer is held administratively down.";
    }

    revision 2026-09-20 {
        description "peer > connection > link-local and peer > attach > process > content > attribute are removed. No code read either one, so both accepted a value at commit and changed nothing.";
    }

    revision 2026-01-01 {
        description "Initial revision";
    }

    typedef capability-mode {
        type enumeration {
            enum enable { ze:help "Advertise the capability; no enforcement"; }
            enum disable { ze:help "Do not advertise the capability; no enforcement"; }
            enum require { ze:help "Advertise the capability; refuse the session when the peer does not offer it"; }
            enum refuse { ze:help "Do not advertise the capability; refuse the session when the peer offers it"; }
        }
        description "The four negotiation modes of one BGP capability. Every mode leaf under capability
            declares this type, so the set is spelled once and parseCapMode in the reactor reads it.";
    }

    // BGP block - main BGP configuration
    container bgp {
        description "A peer inherits from its group defaults. A group inherits from this global level.";
        ze:help "Border Gateway Protocol routing configuration.";

        // Global BGP related tools (workbench). Spec D7/D12.
        // Command paths target the registered command tree: `show bgp health`
        // is a bgp namespace under show; `show warnings` and `show errors` are
        // cross-subsystem report bus snapshots.
        ze:related 'id=bgp-health; label="BGP Health"; command="show bgp health"; placement=global; presentation=modal; class=inspect';
        ze:related 'id=bgp-warnings; label="BGP Warnings"; command="show warnings"; placement=global; presentation=modal; class=diagnose';
        ze:related 'id=bgp-errors; label="BGP Errors"; command="show errors"; placement=global; presentation=modal; class=diagnose';

        leaf router-id {
            type zt:ipv4-address;
            ze:validate "nonzero-ipv4";
            mandatory true;
            description "RFC 6286 Section 2.1 defines the BGP Identifier as a 4-octet, unsigned, non-zero integer. Ze
                therefore rejects 0.0.0.0. A peer that implements RFC 6286 Section 2.2 answers an OPEN that carries
                0.0.0.0 with Bad BGP Identifier. The leaf is mandatory, and a config without it loads only when every
                peer sets session router-id itself or inherits it from its group; a dynamic group must set its own.";
            ze:help "BGP Router ID for this speaker. Required unless every peer or its group sets one.";
        }

        container timer {
            description "BGP timer defaults inherited by groups and peers.";
            ze:help "Session timer defaults inherited by groups and peers.";
            uses delay-open-timer;
        }

        leaf as-notation {
            type enumeration {
                enum asplain { ze:help "Every AS number is a decimal integer"; }
                enum asdot { ze:help "An AS number of 65536 or more is X.Y, and a lower one is a decimal integer"; }
                enum "asdot+" { ze:help "Every AS number is X.Y"; }
            }
            default asplain;
            description "RFC 5396 Section 2 names the three notations. Take AS 65546 and AS 100. asplain
                writes them 65546 and 100. asdot writes 1.10 and 100, leaving an AS number less than 65536
                alone, and asdot+ writes 1.10 and 0.100. The leaf changes the text Ze WRITES, and the
                wire value stays the same 4-octet number (RFC 6793). Ze READS all three notations wherever
                an AS number is configured, and asplain is the default RFC 5396 Section 3 recommends.";
            ze:help "How Ze writes an AS number in the output an operator reads.";
        }

        container multipath {
            description "The container holds maximum-paths and relax-as-path. When maximum-paths is more than 1, Ze
                mirrors the equal-cost siblings of the best path into the shared Loc-RIB. The sysrib component
                expands that set into one ECMP entry in the FIB.";
            ze:help "BGP multipath / ECMP configuration";

            leaf maximum-paths {
                type uint16 {
                    range "1..256";
                }
                default 1;
                description "1 is the default, and it selects the single best path (RFC 4271 Section 9.1.2). A value of more than
                    1 enables ECMP with N-way load balancing.";
                ze:help "Maximum number of equal-cost paths Ze installs per prefix.";
            }

            leaf relax-as-path {
                type boolean;
                default false;
                description "When false, multipath requires an identical AS-path length and identical AS-path content. When true,
                    the AS-path length alone must match, and the content can differ. Other vendors spell this option
                    'bgp bestpath as-path multipath-relax'.";
                ze:help "Treat paths with different AS-paths as equal-cost.";
            }
        }
        container update-delay {
            description "An absent container is the default, and it keeps the behavior Ze had before the container
                existed: each peer advertises as soon as it reaches Established. The container holds max-delay,
                which enables the feature and bounds the wait, and establish-wait, which can end the wait early.
                While Ze holds, sessions negotiate, reach Established and receive UPDATE messages as usual. Ze
                sends no UPDATE and no End-of-RIB marker until the hold ends. RFC 4724 Section 4.1 prescribes
                the same deferral for a speaker that restarts, and requires the configurable upper bound
                max-delay supplies. The hold applies at startup alone: a reload validates a changed value and
                Ze keeps the hold it already armed, or none, so a new value takes effect at the next restart.
                Ze does not enforce a relation between max-delay and the Restart Time it advertises in its
                graceful-restart capability, so keep max-delay below that number yourself. A neighbor whose own
                restart timer expires first discards the routes it kept for Ze. Read `show bgp update-delay` to
                see whether a speaker is holding and what it waits for.";
            ze:help "Hold the first advertisement at startup until the RIB settles.";

            leaf max-delay {
                type uint16 {
                    range "0..3600";
                }
                default 0;
                description "0 is the default and disables the feature. A value of more than 0 arms the hold when the
                    daemon starts its peers. The hold ends when every configured peer sends its End-of-RIB
                    marker, or when establish-wait ends it early, or when these seconds elapse, whichever comes
                    first. Ze waits for the marker and not for Established, because Established says only that
                    the neighbor answered. RFC 4724 Section 4.1 excludes a peer that advertised no
                    graceful-restart capability and a peer that is itself restarting, and Ze excludes the same
                    two. A peer that never comes up cannot extend the wait past this number.";
                ze:help "Seconds to hold the first advertisement. 0 disables the hold.";
            }

            leaf establish-wait {
                type uint16 {
                    range "1..3600";
                }
                description "The leaf is optional, and an absent leaf lets only max-delay and full convergence end
                    the hold. When these seconds elapse and one or more peers are held, Ze ends the hold and
                    advertises to them, whether or not they sent an End-of-RIB marker. When no peer is held, Ze
                    keeps waiting until max-delay, because there is no peer to advertise to yet. Ze refuses a
                    configuration where this value is more than max-delay.";
                ze:help "Seconds after which the peers that are held end the hold. Must not exceed max-delay.";
            }
        }


        container session {
            description "A group value overrides this global value, and a peer value overrides the group value. The
                container holds the local ASN and the shared-router-id switch.";
            ze:help "Global BGP session defaults";
            container asn {
                description "At this global level the container holds the local ASN alone. The same container under a
                    group or a peer also holds remote and local-options.";
                ze:help "AS number configuration";
                leaf local {
                    type zt:asn;
                    mandatory true;
                    ze:decorate "asn-name";
                    description "Ze sends the value as My Autonomous System in OPEN. A group or a peer can override it.
                        Ze keeps this global value for the local-as modifiers, which need the real AS number.";
                    ze:help "Local Autonomous System Number (required)";
                }
            }
            leaf allow-shared-router-id {
                type boolean;
                default false;
                description "The default is false, which enforces AS-wide uniqueness: Ze rejects the second OPEN with Bad BGP
                    Identifier. RFC 6286 Section 2.1 makes AS-wide uniqueness a SHOULD alone, so a shared identifier is
                    conformant. Set the leaf true when the duplication is intentional, for example one anycast speaker
                    (AS112) that peers over both IPv4 and IPv6 with the same router-id. When the leaf is true, Ze skips
                    the AS-wide uniqueness claim alone. RFC 6286 Section 2.2 validation still applies, and it rejects a
                    zero identifier, and this speaker's own identifier from an internal peer. Section 2.3 connection
                    collision resolution is implemented, and this leaf does not disable it.";
                ze:help "Accept a peer whose BGP Identifier duplicates another established peer in the same AS.";
            }
        }

        // The value policy arithmetic starts from for an attribute a route does
        // not carry. The two numbers are declared HERE and nowhere else:
        // bgp-filter-modify reads this container (parseAttributeDefaults,
        // plugins/filter_modify/config.go) and holds no constant of its own.
        container defaults {
            description "The container holds attribute alone today. A default that is not an attribute value gets its own
                container beside it, so an operator's existing leaves never move.";
            ze:help "Values ze supplies when a route carries no such attribute.";

            container attribute {
                description "The leaves govern the arithmetic in policy { modify NAME { increment } } and its
                    decrement sibling alone. They do NOT move the Decision Process: RFC 4271 Section 9.1.2.2 compares
                    an absent MULTI_EXIT_DISC as 0 whatever med says here.

                    There is deliberately no aigp leaf. RFC 7311 Section 4.1 removes a route with no AIGP TLV from
                    consideration rather than scoring it, so no number stands in for the absence. Section 3.4.1
                    forbids ze to add the attribute to a route whose path leads outside the AIGP administrative
                    domain.";
                ze:help "The value policy arithmetic starts from when the route carries no such attribute.";

                leaf med {
                    type uint32 {
                        range "0..4294967295";
                    }
                    default 0;
                    description "RFC 4271 Section 9.1.2.2 supplies this number: \"Routes that do not have the
                        MULTI_EXIT_DISC attribute are considered to have the lowest possible MULTI_EXIT_DISC value.\"
                        A larger value makes an increment write a larger metric onto a route that arrived without one,
                        and the speaker that receives it reads a larger metric as a worse path. The Decision Process
                        comparison stays at 0 whatever this leaf holds.";
                    ze:help "The MULTI_EXIT_DISC value policy arithmetic starts from when the route carries none.";
                }

                leaf local-preference {
                    type uint32 {
                        range "0..4294967295";
                    }
                    default 100;
                    description "RFC 4271 Section 9.1.1 supplies no number: \"The exact nature of this policy information,
                        and the computation involved, is a local matter.\" 100 is the value FRR
                        (BGP_DEFAULT_LOCAL_PREF) and BIRD (default_local_pref) use, and it is the default here for
                        that reason alone. The leaf governs the modifier arithmetic. It does NOT supply the LOCAL_PREF
                        an eBGP-learned route carries into iBGP readvertisement, which ze does not do.";
                    ze:help "The LOCAL_PREF value policy arithmetic starts from when the route carries none.";
                }
            }
        }

        // Global filter chains (apply to all peers as base chain)
        container filter {
            description "The group level and the peer level append to this base chain. A name references a filter instance
                defined under the top-level policy root.";
            ze:help "Global route filter chains for import and export.";
            container import {
                presence "Configure the global import policy.";
                description "Global filters run before group and peer filters. Every configured policy needs a final decision.";
                ze:help "Global import policy";
                uses filter-policy;
            }
            container export {
                presence "Configure the global export policy.";
                description "Global filters run before group and peer filters. The most specific policy supplies the final decision.";
                ze:help "Global export policy";
                uses filter-policy;
            }
        }

        // Global update blocks - default routes applied to all peers.
        // Group and peer levels accumulate additional routes.
        uses update-block;

        // Peer groups - Junos-style: peers nested inside named groups
        list group {
            key "name";
            description "A member peer inherits every leaf of the group, and its own value overrides the inherited one.
                Routes and filter chains accumulate instead of overriding: the group entries run before the peer
                entries.";
            ze:help "Peer group - defines shared defaults for member peers";

            leaf name {
                type string;
                description "A filter can therefore match every peer of one group. A per-group capability block selects
                    its peers by the same name. A rename changes what both select.";
                ze:help "Group name. Ze gives it to an egress filter and to the per-group capability selector.";
            }

            uses peer-fields;

            list peer {
                key "name";
                unique "connection/remote/ip";
                ze:required "connection/remote/ip";
                ze:required "session/asn/local";
                ze:required "session/asn/remote";
                ze:suggest "connection/local/ip";
                description "The list key is the peer name. connection/remote/ip must be unique over every peer, and Ze
                    refuses the config when that address, session/asn/local or session/asn/remote is absent.";
                ze:help "BGP peer in this group";

                // Same workbench tools as standalone bgp/peer, but the
                // selector walks to the parent group's remote IP when the
                // peer omits its own (Spec D7).
                ze:related 'id=peer-detail; label="Peer Detail"; command="peer ${path-inherit:connection/remote/ip|key} detail"; placement=row; presentation=drawer; class=inspect';
                ze:related 'id=peer-capabilities; label="Capabilities"; command="peer ${path-inherit:connection/remote/ip|key} capabilities"; placement=row; presentation=modal; class=inspect';
                ze:related 'id=peer-statistics; label="Statistics"; command="peer ${path-inherit:connection/remote/ip|key} statistics"; placement=row; presentation=modal; class=inspect';
                ze:related 'id=peer-flush; label="Flush"; command="request peer ${path-inherit:connection/remote/ip|key} flush"; placement=row; presentation=modal; class=refresh';
                ze:related 'id=peer-teardown; label="Teardown"; command="request peer ${path-inherit:connection/remote/ip|key} teardown"; placement=row; presentation=modal; confirm="Tear down BGP session?"; class=danger';

                leaf name {
                    type string {
                        pattern '[a-zA-Z0-9_][a-zA-Z0-9_.\-]*';
                    }
                    description "The name is the list key and the CLI selector for the peer. A group member can start
                        with a digit. A standalone peer cannot, because its own pattern requires a letter or an
                        underscore first.";
                    ze:help "Peer name (alphanumeric/underscore start, then alphanumeric/underscore/hyphen/dot)";
                }

                uses peer-fields;
            }
        }

        // Standalone peers (not in a group)
        list peer {
            key "name";
            unique "connection/remote/ip";
            ze:required "connection/remote/ip";
            ze:required "session/asn/local";
            ze:required "session/asn/remote";
            ze:suggest "connection/local/ip";
            description "A standalone peer takes the global level and its own level, so no group value reaches it. The
                list key is the peer name, and connection/remote/ip must be unique over every peer.";
            ze:help "BGP peer configuration (standalone, no group)";

            // Per-row workbench tools (spec Day-One BGP Related Tools).
            // The dispatcher extracts the `peer <selector>` pair and dispatches
            // the remainder against the registered command tree, so commands
            // are written in the form `peer <selector> <verb>` to match
            // `peer/detail`, `peer/capabilities`, etc. from ze-peer-cmd.yang.
            // Selector resolves the peer's remote IP, falling back to the
            // peer's list key when the IP is unset.
            ze:related 'id=peer-detail; label="Peer Detail"; command="peer ${path:connection/remote/ip|key} detail"; placement=row; presentation=drawer; class=inspect';
            ze:related 'id=peer-capabilities; label="Capabilities"; command="peer ${path:connection/remote/ip|key} capabilities"; placement=row; presentation=modal; class=inspect';
            ze:related 'id=peer-statistics; label="Statistics"; command="peer ${path:connection/remote/ip|key} statistics"; placement=row; presentation=modal; class=inspect';
            ze:related 'id=peer-flush; label="Flush"; command="request peer ${path:connection/remote/ip|key} flush"; placement=row; presentation=modal; class=refresh';
            ze:related 'id=peer-teardown; label="Teardown"; command="request peer ${path:connection/remote/ip|key} teardown"; placement=row; presentation=modal; confirm="Tear down BGP session?"; class=danger';

            leaf name {
                type string {
                    pattern '[a-zA-Z_][a-zA-Z0-9_.\-]*';
                }
                description "An underscore is accepted as the first character too. After the first character the name
                    accepts a letter, a digit, an underscore, a hyphen, and a dot.";
                ze:help "Peer name (must start with a letter, not a digit)";
            }

            uses peer-fields;
        }
    }

    grouping delay-open-timer {
        leaf delay-open {
            type uint16 {
                range "0..240";
            }
            default 0;
            description "RFC 4271 DelayOpen: hold a connected socket without sending OPEN until the peer
                sends OPEN or this timer expires. Zero sends OPEN immediately.";
            ze:help "Delay OPEN by 0..240 seconds; 0 disables DelayOpen.";
        }
    }

    // Policy fields are shared by the global, group and peer directions.
    grouping filter-policy {
        description "An ordered filter chain and its required final disposition.";
        leaf-list filters {
            type string { length "1..max"; }
            ordered-by user;
            description "Run these filter references in order after inherited filters. Deactivate a member with inactive: filters NAME.";
            ze:help "Ordered filter instance references";
            ze:reference "policy-filter";
        }
        leaf final {
            type enumeration {
                enum accept { ze:help "Accept a route that passes every filter"; }
                enum reject { ze:help "Reject a route that passes every filter"; }
            }
            mandatory true;
            description "Every present import or export policy must set final accept or final reject, even with no filters.";
            ze:help "Decision after every filter passes";
        }
    }

    // Update block grouping - reused at bgp, group, and peer levels.
    grouping update-block {
        // Native update syntax - Ze-native route announcements
        // update { attribute { origin igp; next-hop 10.0.0.1; } nlri { ipv4/unicast 1.0.0.0/24; } }
        list update {
            description "Ze announces every route of the block to the peers the block applies to. The block is written
                at the global level, the group level, and the peer level, and the three accumulate.";
            ze:help "Native Ze route announcements";

            leaf name {
                type string {
                    pattern '[a-zA-Z0-9_][a-zA-Z0-9_.\-]*';
                }
                ze:display-key;
                description "The list carries no key, so the CLI and the web UI show this label in place of one. The
                    label reaches no BGP message.";
                ze:help "Optional label for this update block (display only)";
            }

            container attribute {
                description "Every NLRI of the block takes the same attributes. To announce two prefixes that carry
                    different attributes, write two update blocks.";
                ze:help "Path attributes for routes in this block";
                leaf origin {
                    type enumeration {
                        enum igp { ze:help "Interior Gateway Protocol"; }
                        enum egp { ze:help "Exterior Gateway Protocol"; }
                        enum incomplete { ze:help "Incomplete origin"; }
                    }
                    description "RFC 4271 Section 4.3 gives three values. igp is reachability interior to the
                        originating AS. egp is reachability learned through the EGP protocol. incomplete is
                        reachability learned by some other means, for example a redistributed static route.";
                    ze:help "ORIGIN attribute (RFC 4271 Section 4.3)";
                }
                leaf next-hop {
                    type union {
                        type zt:ip-address;
                        type enumeration {
                            enum self { ze:help "Resolve the next hop at send time to the local address of each session."; }
                        }
                    }
                    description "self resolves at send time to the local address of the session, so each peer reads its
                        own next hop. An IP address reaches every peer of the block unchanged. Ze refuses an IPv6
                        link-local address here, because RFC 2545 Section 3 puts the global address in that field.";
                    ze:help "Next hop address or 'self'";
                }
                leaf med { type uint32; description "MED influences the inbound path selection that an external peer makes (RFC 4271 Section 5.1.4).";
 ze:help "Multi-Exit Discriminator (MED). The lower value is preferred."; }
                leaf local-preference { type uint32; description "LOCAL_PREF has a meaning inside a single AS alone (RFC 4271 Section 5.1.5). The default is 100.";
 ze:help "LOCAL_PREF value for iBGP best-path selection. The higher value wins."; }
                leaf-list as-path { type string; ze:ordered; description "The list is an ordered sequence. A repeated ASN is a prepend that counts, so Ze does not deduplicate
     it (RFC 4271 Section 5.1.2). AS_PATH decides loop detection, and it decides path selection, where
     the shorter path is preferred.";
 ze:help "AS_PATH segments prepended to the route, as space-separated ASNs."; }
                leaf-list community { type string; description "The format is AS:value, for example 65000:100. A well-known name is also accepted, such as no-export
     or no-advertise.";
 ze:help "Standard BGP communities (RFC 1997)."; }
                leaf-list large-community { type string; description "Each value is three 32-bit numbers separated by colons, which is 12 octets on the wire. The global part
     holds a 4-byte ASN, which a standard community of RFC 1997 cannot hold.";
 ze:help "Large BGP communities (RFC 8092). Format: global:local1:local2. Supports 4-byte ASNs natively."; }
                leaf-list extended-community { type string; description "An extended community carries a route target, a site-of-origin, or VPN semantics.";
 ze:help "Extended communities (RFC 4360). The format is type:admin:value."; }
                leaf label { type string; description "Ze accepts a decimal number from 0 to 1048575, which is the 20-bit label field. It accepts no keyword.
     Write the labels leaf-list for a stack of more than one label.";
 ze:help "MPLS label value for a labeled unicast route (RFC 3107). The value is a number."; }
                leaf-list labels { type string; ze:ordered; description "The list is an ordered sequence from bottom to top. Ze keeps a repeated label, and it does not
     deduplicate the stack.";
 ze:help "MPLS label stack for a multi-label route (RFC 8277)."; }
                leaf path-information { type string; description "The identifier separates the several paths that one peer sends for the same prefix.";
 ze:help "ADD-PATH path identifier (RFC 7911)."; }
                leaf rd { type zt:route-distinguisher; description "Ze prepends the Route Distinguisher to the prefix, which makes a unique VPN route.";
 ze:help "Route Distinguisher (RFC 4364). The format is ASN:nn or IP:nn."; }
                leaf aggregator { type string; description "The attribute identifies the AS and the router that formed the aggregate.";
 ze:help "AGGREGATOR attribute (RFC 4271 Section 5.1.7). The format is AS:IP."; }
                leaf atomic-aggregate { type boolean; description "The flag signals that aggregation formed the route, and that AS_PATH information was lost.";
 ze:help "ATOMIC_AGGREGATE flag (RFC 4271 Section 5.1.6)."; }
                leaf originator-id { type zt:ipv4-address; description "The reflector sets the attribute to the router ID of the originating router. The attribute prevents
     a loop.";
 ze:help "ORIGINATOR_ID for route reflection (RFC 4456)."; }
                leaf-list cluster-list { type zt:ipv4-address; description "Each reflector prepends its cluster ID. The list detects a loop between reflectors.";
 ze:help "CLUSTER_LIST for route reflection (RFC 4456)."; }
                leaf-list attribute { type string; description "The list carries an attribute that no named field covers.";
 ze:help "Raw BGP attribute: [ 0x<code> 0x<flags> 0x<value> ]."; }
                container bgp-prefix-sid { presence "Prefix-SID enabled"; description "The attribute carries an MPLS label index for Segment Routing. A node can therefore advertise its
     SID without a per-prefix label allocation.";
 ze:help "Prefix-SID attribute (RFC 8669)."; }
                container bgp-prefix-sid-srv6 { presence "SRv6 Prefix-SID enabled"; description "The attribute carries SRv6 SID information for IPv6 Segment Routing, and it includes the SRv6 L3
     Service TLVs.";
 ze:help "SRv6 Prefix-SID attribute (RFC 9252)."; }
                leaf split { type string; description "The format is /length. For example, /24 splits a /16 into 256 prefixes of /24.";
 ze:help "Split one prefix into more-specific prefixes for the announcement."; }
            }

            list nlri {
                key "name";
                description "Every entry takes the attribute block of the update block. The key is the family name, and
                    content carries the operation keyword and the prefixes. An update block that declares no nlri
                    entry is refused at config load.";
                ze:help "Routes this update block announces, one entry for each address family.";
                leaf name { type zt:address-family; description "The name is a registered address family. Ze refuses an unregistered name at config load.";
 ze:help "Address family (e.g., ipv4/unicast)"; }
                leaf content { type string; description "The form is an operation keyword, then an optional rd and label, then one or more prefixes. add, del and
     eor are the operation keywords, and one of them is required. A block that carries del or eor announces nothing
     at config load.";
 ze:help "Operation, qualifiers, and payload"; }
            }

            container watchdog {
                description "The bgp-watchdog plugin owns every route of the block, so the BGP engine holds none of
                    them as a static route. The plugin sends a route that is not withdrawn when the session reaches
                    Established.";
                ze:help "Watchdog-controlled route - held until 'bgp watchdog announce <name>'";
                leaf name { type string; description "request bgp watchdog announce <name> announces every route that carries the name, and request bgp
     watchdog withdraw <name> withdraws them. Ze skips a block whose name is empty.";
 ze:help "Watchdog group name"; }
                leaf withdraw { type boolean; description "The bgp-watchdog plugin reads the PRESENCE of the leaf and not its value, so withdraw false starts every
     route of the block withdrawn exactly as withdraw true does. Delete the leaf to announce the routes as soon as
     the session reaches Established. request bgp watchdog announce <name> announces a withdrawn route.";
 ze:help "Start in withdrawn state (default true)"; }
            }
        }
    }

    // Shared fields for both groups and peers (no IP addresses).
    grouping peer-fields {
        description "Common peer/group configuration fields";

        // Connection container - transport-level settings
        container connection {
            description "The container holds the local endpoint, the remote endpoint, the TCP MD5 key, the TTL
                controls, and the BFD opt-in. connect and accept cannot both be false, and Ze refuses that config.";
            ze:help "Transport-level connection settings";

            container local {
                description "The container controls the bind address, the port, and whether Ze accepts an inbound connection.";
                ze:help "Local endpoint for the TCP session.";
                leaf ip {
                    type union {
                        type zt:ip-address;
                        type enumeration {
                            enum auto { ze:help "Let the operating system choose the source address of the connection."; }
                        }
                    }
                    description "auto leaves the source address to the operating system. An address binds the outbound
                        connection to it, which fixes the source address that a next-hop self rewrite uses. Ze
                        refuses an IPv6 link-local address here.";
                    ze:help "Local address for connection (use IP address or 'auto')";
                }
                leaf port {
                    type zt:port;
                    description "Ze opens a listener of its own for this peer on the local address and this port, and
                        answers an inbound connection there. The default is 179, and a peer at 179 shares the
                        global listener. The range is 1 to 65535, and Ze refuses a config outside it. Ze binds no
                        local source port on an outbound connection, so the value applies to the listener alone.
                        connection > remote > port is the port Ze dials, and the two are independent.";
                    ze:help "Local listen port";
                }
                leaf accept {
                    type boolean;
                    default true;
                    description "The default is true. Set the leaf false for a peer Ze dials and never answers. accept
                        and connect cannot both be false, and Ze refuses that config.";
                    ze:help "Accept inbound TCP connections at this local endpoint (RFC 4271 Section 8.1.1)";
                }
            }

            container remote {
                description "The container controls the peer address, the port, the outbound connection, and the dynamic peer
                    ranges.";
                ze:help "Remote endpoint for the TCP session.";
                leaf ip {
                    type union {
                        type zt:ip-address;
                        type enumeration {
                            enum dynamic {
                                description "The group accepts a session from any address in its range. The
                                             value is valid at group level only and is rejected on a peer.";
                                ze:help "Accept BGP sessions from any IP in the group's range.";
                            }
                        }
                    }
                    ze:decorate "reverse-dns";
                    description "dynamic is valid at the group level alone. Ze then creates a peer when a connection
                        arrives from an address inside one of the ranges, up to max-peers. The address must be
                        unique over every peer.";
                    ze:help "Peer IP address or 'dynamic' for dynamic peer groups";
                }
                leaf port {
                    type zt:port;
                    description "The default is 179. Ze dials the peer at this port. Set the leaf for a peer that
                        listens on another port, and for a test peer on one host. connection > local > port is
                        the port Ze listens on, and the two are independent.";
                    ze:help "Remote connection port";
                }
                leaf connect {
                    type boolean;
                    default true;
                    description "The default is true. Set the leaf false for a passive peer that Ze answers and never
                        dials. connect and accept cannot both be false, and Ze refuses that config.";
                    ze:help "Initiate outbound TCP connections to this remote endpoint (RFC 4271 Section 8.1.1)";
                }
                leaf-list range {
                    type zt:ip-prefix;
                    description "The list has a meaning when ip is 'dynamic' alone. A connection from an IP address inside one of
                        these ranges creates a dynamic peer.";
                    ze:help "IP prefix ranges for a dynamic peer group.";
                }
                leaf max-peers {
                    type uint32 {
                        range "1..100000";
                    }
                    default 1000;
                    description "The default is 1000, and the range is 1 to 100000. The leaf has a meaning when ip is
                        dynamic alone. Ze refuses a connection that would take the group past the value.";
                    ze:help "Maximum number of dynamic peers for this group";
                }
            }

            container md5 {
                description "Ze applies TCP_MD5SIG to the dialing socket and to the listening socket. A peer with no
                    matching key cannot open the TCP connection, so the session never reaches OPEN.";
                ze:help "TCP MD5 authentication (RFC 2385)";
                leaf password {
                    type string;
                    ze:sensitive;
                    description "The leaf is marked sensitive, so the CLI and the web UI hide the value. The key never
                        reaches the wire, because RFC 2385 carries a digest in a TCP option.";
                    ze:help "MD5 authentication password";
                }
                leaf ip {
                    type zt:ip-address;
                    description "The default is the peer address. Set the leaf for a multi-hop peer whose key is bound
                        to another address.";
                    ze:help "MD5 authentication IP";
                }
            }

            container ttl {
                description "max is the hop-count form of RFC 5082 GTSM. set and min are the two raw values. Ze refuses
                    max together with set, and max together with min.";
                ze:help "TTL settings for BGP sessions";
                leaf max {
                    type uint8;
                    description "The value is a hop count. Ze sends every packet with TTL 255, and the kernel refuses a
                        packet that arrives with less than 256 minus the value. max 1 therefore accepts a directly
                        connected peer alone.";
                    ze:help "TTL security / GTSM (RFC 5082)";
                }
                leaf set {
                    type uint8;
                    description "0 leaves the operating system default in place. A value sets the IP TTL, or the IPv6
                        Hop Limit, on every packet Ze sends to this peer.";
                    ze:help "Outgoing TTL value";
                }
                leaf min {
                    type uint8;
                    description "0 installs no receive-side gate in the kernel. A value makes the kernel refuse a
                        packet whose IP TTL, or IPv6 Hop Limit, is less than it.";
                    ze:help "Minimum incoming TTL";
                }
            }

            container bfd {
                presence "Enable BFD liveness detection for this peer";
                description "When the container is present, the BGP reactor calls the Service interface of the BFD plugin at
                    session establishment. The reactor stops the BGP session when BFD reports Down. The BFD plugin must
                    be loaded through a top-level bfd { ... } block. A config that opts a peer in while that block is
                    absent or sets enabled false is refused, naming the peer.";
                ze:help "Bidirectional Forwarding Detection options for this peer (RFC 5880).";

                leaf enabled {
                    type boolean;
                    default true;
                    description "Set the leaf false to keep the config in place and suspend the BFD client. This is useful during
                        maintenance.";
                    ze:help "Master switch for the BFD session of this peer.";
                }

                leaf mode {
                    type enumeration {
                        enum single-hop {
                            ze:help "RFC 5881 single-hop BFD on UDP 3784 with GTSM.";
                        }
                        enum multi-hop {
                            ze:help "RFC 5883 multi-hop BFD on UDP 4784 with min-TTL.";
                        }
                    }
                    default single-hop;
                    description "Single-hop is the common case for an eBGP peer on a direct link. Multi-hop is for iBGP over an IGP,
                        and for any peering that crosses more than one IP hop.";
                    ze:help "BFD hop mode for this peer: single-hop or multi-hop.";
                }

                leaf profile {
                    type string;
                    ze:reference "bfd-profile";
                    description "The referenced profile supplies the session's detect-multiplier, desired-min-tx-us,
                        required-min-rx-us, passive role, authentication and echo interval, and replaces whatever the peer
                        would otherwise use. Commit, ze config validate and a SIGHUP reload refuse a name no bfd profile
                        defines, naming the profiles that exist; the editor completes those names. The leaf names a list
                        of another module that a build without BFD leaves out, so it is a ze:reference, not a leafref.
                        The running daemon also refuses to start, and refuses a commit or a SIGHUP reload, when the profile
                        sets passive on a single-hop peer (RFC 5881 Section 3), or when it enables echo on a multi-hop peer
                        (RFC 5883 Section 3); ze config validate does not run that check. Without this leaf the session
                        takes the BFD plugin defaults.";
                    ze:help "Name of a profile defined under the top-level bfd { profile ... } block.";
                }

                leaf min-ttl {
                    type uint8;
                    description "Ze ignores the leaf for single-hop. Zero selects the plugin default, which is 254.";
                    ze:help "Multi-hop minimum acceptable TTL (RFC 5883 Section 5).";
                }

                leaf interface {
                    type string;
                    description "The leaf is optional. When the leaf is absent, the BFD plugin derives the interface from the local
                        address of the peer. Ze ignores the leaf for multi-hop.";
                    ze:help "Single-hop egress interface for the BFD session.";
                }

                leaf strict {
                    type boolean;
                    default false;
                    description "Ze advertises BGP capability 74 in its OPEN and does not let the BGP session go past OpenSent until
                        the BFD session is Up. Both speakers must advertise the capability: against a peer that does not, Ze
                        establishes the session on the normal path and BFD stays a failure detector. Ze opens the BFD session
                        before it starts the BGP FSM, and keeps it open while the BGP session is down.";
                    ze:help "BFD strict mode (draft-ietf-idr-bgp-bfd-strict-mode).";
                }

                leaf hold-down {
                    type uint32;
                    units milliseconds;
                    default 0;
                    description "How long the BFD session must stay Up before Ze lets the BGP session establish. Zero, the default,
                        establishes on the first Up and is the behaviour of a peer that sets no hold-down. A non-zero value damps
                        a flapping link: a BFD session that goes down again inside the interval never completes it. Set the
                        negotiated BGP hold time long enough to cover this interval, or the far end times out waiting.";
                    ze:help "BFD hold-down interval for strict mode (draft-ietf-idr-bgp-bfd-strict-mode Section 10).";
                }

                leaf hold-time {
                    type uint16 {
                        range "1..65535";
                    }
                    units seconds;
                    default 30;
                    description "The maximum time Ze waits for BFD to come Up after the peer's OPEN, and only when the negotiated BGP
                        hold time is zero. A non-zero BGP hold time bounds the wait already, so this timer does not run. On
                        expiry Ze sends a NOTIFICATION with Cease and subcode BFD Down, and the peer returns to Idle.";
                    ze:help "BfdHoldTime for strict mode (draft-ietf-idr-bgp-bfd-strict-mode Section 3).";
                }
            }
        }

        // Session container - BGP session settings
        container session {
            description "The container holds the ASN, the capabilities, the address families, the next-hop policy, and the
                community control. A peer inherits these from its group, and a peer value overrides the group value.";
            ze:help "BGP session parameters for this peer or group.";

            container aigp {
                description "RFC 7311 session boundary and origination policy. Enable external sessions only inside one AIGP administrative domain.";
                ze:help "Accumulated IGP metric policy for this session.";
                leaf enabled {
                    type boolean;
                    description "Overrides AIGP_SESSION. Without this leaf, internal sessions enable AIGP and external sessions disable it.";
                    ze:help "Accept and send AIGP on this session.";
                }
                leaf originate {
                    type boolean;
                    default false;
                    description "Permit explicitly supplied AIGP metrics only on domain-local routes advertised with this speaker as next hop.";
                    ze:help "Permit AIGP attribute origination.";
                }
                leaf link-metric {
                    type uint64 { range "1..max"; }
                    description "Distance to this peer when no IGP provides one. Use units comparable to the administrative domain's IGP metrics.";
                    ze:help "Non-zero metric for a link without an IGP.";
                }
                leaf-list domain-as {
                    type zt:asn;
                    description "External ASes inside the AIGP administrative domain. A newly originated attribute cannot accompany a path containing any other external AS.";
                    ze:help "External AS numbers inside the AIGP domain.";
                }
            }

            leaf as-set {
                type enumeration {
                    enum withdraw { ze:help "Treat a received AS_SET or AS_CONFED_SET as withdrawn (RFC 9774)"; }
                    enum accept { ze:help "Keep a received AS_SET or AS_CONFED_SET, as ExaBGP as-set accept did"; }
                }
                default withdraw;
                description "RFC 9774 Section 3 treats an UPDATE whose AS_PATH or AS4_PATH holds an AS_SET or
                    AS_CONFED_SET as withdrawn, unless explicitly configured otherwise by a network operator.
                    accept is that operator configuration: the operator sets it on a peer that must keep such
                    routes, and ze exabgp migrate writes it for a neighbor whose ExaBGP config said as-set
                    accept. Every other check of the path still runs, and Ze still never advertises a set to
                    this peer.";
                ze:help "Received AS_SET handling; accept keeps such a route, as the operator configured.";
            }

            container asn {
                description "local overrides the global ASN for this session. remote names the peer ASN. Ze compares
                    the two to decide whether the session is eBGP or iBGP. migration names a second local ASN this
                    iBGP session also accepts while the router moves from one ASN to another.";
                ze:help "AS number configuration";
                leaf local {
                    type zt:asn;
                    ze:decorate "asn-name";
                    description "Ze sends this value in OPEN in place of the global ASN. Ze keeps the global ASN too,
                        and local-options decides how the two appear in AS_PATH.";
                    ze:help "Local AS (overrides global)";
                }
                leaf remote {
                    type zt:asn;
                    ze:decorate "asn-name";
                    description "Ze compares the value with the local ASN. A different value makes the session eBGP,
                        and an equal value makes it iBGP. That verdict decides the AS_PATH prepend, the auto
                        next-hop rewrite, and whether Ze sends LOCAL_PREF.";
                    ze:help "Peer Autonomous System Number";
                }
                leaf migration {
                    type zt:asn;
                    ze:decorate "asn-name";
                    description "RFC 7705 Section 4.2 'Internal BGP AS Migration'. Set the leaf to the other ASN of the
                        pair the router runs while it moves from one ASN to another: the local ASN is one of the two
                        and this leaf is the other. Ze then accepts an OPEN whose My Autonomous System carries either
                        ASN, and treats the session as native iBGP whichever ASN won. Ze sends the local ASN first and
                        falls back to this one only after the peer answers Bad Peer AS, which is what keeps two
                        speakers that both run the mechanism from deadlocking. remote must name one of the two ASNs,
                        and Ze refuses a config where it names a third. Remove the leaf when the migration ends.";
                    ze:help "Second local AS this iBGP session accepts and sends during an AS migration.";
                }
                leaf-list local-options {
                    type enumeration {
                        enum no-prepend {
                            description "RFC 7705 Section 3.3 'No Prepend Inbound': the local-as is
                                         not added to a route received from this peer, so it is
                                         absent when the route is installed and when it goes to an
                                         iBGP neighbor. Ze never adds an AS to a received AS_PATH,
                                         so this option states the behavior ze already has. It does
                                         not change what this peer receives.";
                            ze:help "Do not add the local-as to a route received from this peer.";
                        }
                        enum replace-as {
                            description "RFC 7705 Section 3.3 'Replace Old AS': toward this peer the
                                         globally configured ASN is not prepended, and the local-as
                                         is the only AS number added to AS_PATH.";
                            ze:help "Send the local-as alone toward this peer, without the global ASN.";
                        }
                    }
                    description "The two options act in different directions, so each one is set on its own. no-prepend acts inbound:
                        the local-as is not added to a route received from this peer. replace-as acts outbound: this peer
                        sees the local-as alone instead of the local-as followed by the globally configured ASN. With
                        neither option, this peer sees the local-as followed by the globally configured ASN.";
                    ze:help "Modifiers for the local-as behavior of this peer.";
                }
            }

            leaf as-override {
                type boolean;
                default false;
                description "Use the leaf in a VPN design, or in a multi-site design, where the same customer ASN appears at more
                    than one site.";
                ze:help "Replace the ASN of the peer with the local ASN in the outbound AS_PATH.";
            }

            leaf accept-srv6-prefix-sid {
                type boolean;
                default false;
                description "RFC 8669 Section 4 states that a PrefixSID from an EBGP peer outside the SR domain MUST be
                    discarded, unless the speaker is configured to accept it. The leaf has no effect on IBGP, where Ze
                    always accepts the attribute.";
                ze:help "Accept the BGP Prefix-SID attribute (code 40) with SRv6 TLVs from this EBGP peer.";
            }

            leaf propagate-srv6-prefix-sid {
                type boolean;
                default false;
                description "RFC 8669 Section 8 states that the propagation to another AS MUST be configured explicitly. Ze
                    therefore removes the attribute from every UPDATE sent to an EBGP peer that does not set this leaf.
                    Set the leaf on an EBGP peer inside the same SR domain. An SR domain can span more than one AS, and
                    Ze cannot derive that membership from the ASN. The leaf has no effect on IBGP, where Ze always
                    advertises the attribute.";
                ze:help "Advertise the BGP Prefix-SID attribute (code 40) to this EBGP peer.";
            }

            container community {
                description "The container holds the send leaf-list alone. send names the community types Ze puts in an
                    outbound UPDATE, and it acts on no inbound message.";
                ze:help "Community attribute control for this session";
                leaf-list send {
                    type enumeration {
                        enum standard {
                            ze:help "Send standard communities (type 8, RFC 1997)";
                        }
                        enum large {
                            ze:help "Send large communities (type 32, RFC 8092)";
                        }
                        enum extended {
                            ze:help "Send extended communities (type 16, RFC 4360)";
                        }
                        enum all {
                            ze:help "Send all community types (default)";
                        }
                        enum none {
                            ze:help "Suppress all community attributes";
                        }
                    }
                    description "The default is all, which sends every community type. Name an individual type to control the set.
                        none suppresses every community attribute.";
                    ze:help "Community types Ze includes in an outbound UPDATE.";
                }
            }

            leaf router-id {
                type zt:ipv4-address;
                ze:validate "nonzero-ipv4";
                description "RFC 6286 Section 2.1 defines the BGP Identifier as a 4-octet, unsigned, non-zero integer, so Ze
                    rejects 0.0.0.0. The same section says the identifier is the same for every BGP peer; this override
                    departs from that, by owner decision: a peer or group that sets it sends its own identifier in its
                    OPEN instead of the global router-id.";
                ze:help "Override the router ID for this peer.";
            }

            leaf route-reflector-client {
                type boolean;
                default false;
                description "Ze forwards a route from a client to every client and to every non-client. Ze forwards a route from
                    a non-client to the clients alone.";
                ze:help "Mark this peer as a route reflector client (RFC 4456).";
            }

            leaf cluster-id {
                type zt:ipv4-address;
                description "The default is the router-id. Ze prepends the cluster ID to CLUSTER_LIST on a reflected route.";
                ze:help "Override the cluster ID for route reflection (RFC 4456 Section 7).";
            }

            leaf next-hop {
                type union {
                    type zt:ip-address;
                    type enumeration {
                        enum self {
                            ze:help "Rewrite next-hop to local address (common for iBGP)";
                        }
                        enum unchanged {
                            ze:help "Never rewrite next-hop (route-server, third-party NH)";
                        }
                        enum auto {
                            ze:help "RFC 4271 default: rewrite for eBGP, preserve for iBGP";
                        }
                    }
                }
                default "auto";
                description "auto rewrites the next hop for an eBGP peer, and preserves it for an iBGP peer. self always rewrites
                    the next hop to the local address. unchanged never rewrites it, so the original next hop is
                    preserved. An IP address sets the next hop to that address.";
                ze:help "Next-hop rewriting policy for a forwarded UPDATE (RFC 4271 Section 5.1.3).";
            }

            leaf link-local {
                type zt:ipv6-address;
                description "The address goes in the MP_REACH Next Hop field. The leaf supplies the address, and it does not
                    decide that the address is sent. Ze appends the address only when this speaker shares a locally
                    connected subnet with the peer, and with the entity that the global next hop names. That is the 'if
                    and only if' condition of Section 3. In every other case the field carries the global address alone.
                    Set the leaf on a session that faces a peer on a shared link. It has no effect on any other session.";
                ze:help "IPv6 link-local address advertised after the global next hop (RFC 2545 Section 3).";
            }

            // Address families
            list family {
                key "name";
                description "Ze advertises one Multiprotocol Extensions capability per entry (RFC 4760). A list with no
                    entry sends no such capability. Each entry also carries the prefix limit and the
                    default-originate switch of that family.";
                ze:help "Address families to negotiate";
                leaf name {
                    type zt:address-family;
                    ze:validate "registered-address-family";
                    description "The value must name a family the binary registered. Ze refuses an unregistered name at
                        config load, so a family that a missing plugin owns is reported rather than dropped.";
                    ze:help "AFI/SAFI (e.g. ipv4/unicast)";
                }
                leaf mode {
                    type enumeration {
                        enum enable { ze:help "Enable this address family"; }
                        enum disable { ze:help "Disable this address family"; }
                        enum require { ze:help "Require this address family"; }
                        enum ignore { ze:help "Ignore this address family"; }
                    }
                    description "enable advertises the family. disable does not advertise it. require advertises it and
                        refuses the session when the peer does not offer it. ignore advertises the family and
                        relaxes the UPDATE check. Ze then drops an UPDATE that names a family the two peers did
                        not negotiate, and the session stays up.";
                    ze:help "Address family negotiation mode";
                }

                // Per-family prefix limits (RFC 4486)
                container prefix {
                    description "The limit is the defense against a peer that floods the RIB. When the count crosses
                        maximum, Ze sends a Cease NOTIFICATION with subcode 1, Maximum Number of Prefixes Reached
                        (RFC 4486).";
                    ze:help "Prefix limit configuration for this address family";
                    leaf maximum {
                        type uint32 {
                            range "1..max";
                        }
                        description "The NOTIFICATION data carries the AFI, the SAFI, and this value as the upper bound
                            (RFC 4486 Section 4). The count leaf decides which prefixes the count holds.";
                        ze:help "Hard maximum number of prefixes accepted";
                    }
                    leaf warning {
                        type uint32;
                        description "Crossing the threshold raises a metric and a login-banner warning, and it leaves
                            the session up. Ze refuses a warning value that is not less than maximum.";
                        ze:help "Warning threshold. Defaults to 90% of maximum when not set.";
                    }
                    leaf teardown {
                        type boolean;
                        default true;
                        description "The default is true, and an absent value also reads as true. With false Ze keeps
                            the session up and drops the UPDATE that crossed the maximum.";
                        ze:help "Tear down session when prefix maximum exceeded (false = warn only)";
                    }
                    leaf count {
                        type enumeration {
                            enum offered {
                                description "Count every announcement the peer sends, the announcements of a
                                             dropped UPDATE included. A prefix announced twice counts twice.";
                                ze:help "Count every announcement the peer sends, repeats included.";
                            }
                            enum installed {
                                description "Count the prefixes this family currently holds. A re-announced
                                             prefix is one prefix, a dropped UPDATE moves nothing, and a
                                             withdrawal of a prefix ze does not hold moves nothing.";
                                ze:help "Count the prefixes this family holds now.";
                            }
                        }
                        default "offered";
                        description "offered counts wire events. Every announcement raises the count, and every withdrawal lowers it. A
                            peer that re-announces a prefix to change an attribute raises the count again, although it holds the
                            same route. The count can therefore be more than the maximum. Ze then drops every later announce of
                            this family, until the peer withdraws enough prefixes. installed counts the set of prefixes Ze
                            currently holds for this family, which no re-announcement and no unmatched withdrawal can move.
                            installed keeps one entry per prefix for this family, so its memory is the size of what the peer
                            sends, up to the maximum. Neither value is the size of the RIB, because import policy can reject a
                            counted prefix.";
                        ze:help "Which prefixes the count compared against maximum holds.";
                    }
                    leaf idle-timeout {
                        type uint16;
                        default 0;
                        description "The wait doubles on each repeat teardown, up to one hour. 0 keeps the peer down. See the reconnect
                            leaf.";
                        ze:help "Seconds to wait before reconnect after this family stopped the session.";
                    }
                    leaf reconnect {
                        type enumeration {
                            enum never { ze:help "Keep the peer down. An operator restarts it."; }
                            enum backoff { ze:help "Reconnect on the usual connect backoff of the peer."; }
                            enum timer { ze:help "Reconnect after idle-timeout seconds."; }
                        }
                        description "No value means timer when idle-timeout is more than 0, and never when idle-timeout is 0.";
                        ze:help "What the peer does after this family stopped the session.";
                    }
                    leaf updated {
                        type string;
                        ze:hidden true;
                        description "ze:hidden keeps the leaf out of the CLI completion. The peer command reports the
                            date, and it marks the peer prefix-stale when the date is more than 180 days old.";
                        ze:help "ISO date (YYYY-MM-DD) when prefix maximum was last updated from PeeringDB. Hidden leaf.";
                    }
                }

                leaf default-originate {
                    type boolean;
                    default false;
                    description "The default route is 0.0.0.0/0 for IPv4, and ::/0 for IPv6.";
                    ze:help "Originate the default route to this peer for this address family.";
                }

                leaf default-originate-filter {
                    type string;
                    description "When the filter rejects, Ze does not send the default route. An empty value, or an absent leaf,
                        originates the default route without a condition.";
                    ze:help "Named filter that must accept before Ze originates the default route.";
                }
            }

            // Capabilities
            container capability {
                description "Every capability here takes four modes. enable advertises it. disable does not advertise
                    it. require advertises it and refuses the session when the peer does not offer it. refuse does
                    not advertise it and refuses the session when the peer offers it.";
                ze:help "BGP capability negotiation";

                leaf asn4 {
                    type capability-mode;
                    default enable;
                    description "The capability is required for an ASN of more than 65535. Disable it only for a peer that runs a
                        legacy implementation, which speaks 2-byte ASNs alone. require refuses the session when the
                        peer does not offer it, and refuse refuses the session when the peer offers it.";
                    ze:help "4-byte ASN capability mode (RFC 6793): enable, disable, require or refuse.";
                }

                leaf route-refresh {
                    type capability-mode;
                    description "The capability lets the peer request a full re-advertisement of the routes, without a session
                        teardown. enable also advertises Enhanced Route Refresh (RFC 7313). Absent means not advertised.";
                    ze:help "Route Refresh capability mode (RFC 2918): enable, disable, require or refuse.";
                }

                // NOTE: graceful-restart moved to GR plugin (ze-graceful-restart.yang)

                container add-path {
                    presence "ADD-PATH capability enabled";
                    description "PATHS-LIMIT is draft-abraitis-idr-addpath-paths-limit. The default direction applies to every
                        negotiated multiprotocol family. A per-family entry overrides the default direction.";
                    ze:help "ADD-PATH capability (RFC 7911), with an optional PATHS-LIMIT.";
                    leaf direction {
                        type enumeration {
                            enum send { ze:help "Send multiple paths"; }
                            enum receive { ze:help "Receive multiple paths"; }
                            enum send/receive { ze:help "Both send and receive multiple paths"; }
                        }
                        description "send offers more than one path to the peer. receive accepts more than one path
                            from the peer. send/receive does both. Ze applies the value to every negotiated family
                            that carries no family entry of its own.";
                        ze:help "Default ADD-PATH direction for all negotiated families.";
                    }
                    container limit {
                        description "Holds the path counts per prefix for each ADD-PATH direction. A per-family limit
                            container overrides a value set here. Only the receive direction exists today.";
                        ze:help "Default PATHS-LIMIT path counts per prefix, by direction.";
                        leaf receive {
                            type uint16 { range "1..65535"; }
                            description "Ze advertises this receive request in PATHS-LIMIT for each enabled ADD-PATH
                                family whose direction includes receive. A per-family receive overrides it. Ze also
                                enforces it: a path over the limit for one prefix is dropped on arrival.";
                            ze:help "Default maximum paths per prefix requested from the peer (PATHS-LIMIT).";
                        }
                    }
                    list family {
                        key "name";
                        description "The list key is the family name. An entry with no direction takes the container
                            direction. Ze skips an entry whose family name is not registered.";
                        ze:help "Per-family ADD-PATH overrides with an optional path count limit.";
                        leaf name { type zt:address-family; description "The name is the list key. Ze looks it up in the family registry, and it skips the whole entry when the
     lookup fails.";
 ze:help "Address family (e.g. ipv4/unicast)"; }
                        leaf direction {
                            type enumeration {
                                enum send { ze:help "Send ADD-PATH"; }
                                enum receive { ze:help "Receive ADD-PATH"; }
                                enum send/receive { ze:help "Both send and receive ADD-PATH"; }
                            }
                            description "The value replaces the container direction for this family. An absent value
                                keeps the container direction.";
                            ze:help "ADD-PATH direction override for this family.";
                        }
                        container limit {
                            description "Holds this family's path counts per prefix for each ADD-PATH direction. A
                                value set here replaces the container limit for this family alone.";
                            ze:help "PATHS-LIMIT path counts per prefix for this family, by direction.";
                            leaf receive {
                                type uint16 { range "1..65535"; }
                                description "Use a value from 1 through 65535. Omit this leaf to inherit the container
                                    receive limit. Ze advertises no limit for a disabled or refused ADD-PATH family, or
                                    for one whose direction excludes receive. Ze also enforces it on arrival: a path over
                                    the limit for one prefix is dropped, and the rest of its UPDATE installs.";
                                ze:help "Maximum paths per prefix requested from the peer (PATHS-LIMIT capability).";
                            }
                        }
                        leaf mode {
                            type capability-mode;
                            description "enable and disable act on this family alone. require refuses the session when
                                the peer does not offer ADD-PATH. refuse refuses the session when the peer offers
                                it. Ze takes the most restrictive mode over the whole list.";
                            ze:help "ADD-PATH negotiation mode for this family.";
                        }
                    }
                }

                leaf extended-message {
                    type capability-mode;
                    description "The capability raises the BGP message size limit from 4096 bytes to 65535 bytes. A large UPDATE that
                        carries many attributes needs it. Absent means not advertised.";
                    ze:help "Extended Message capability mode (RFC 8654): enable, disable, require or refuse.";
                }

                list nexthop {
                    key "family";
                    description "The list key is the NLRI family, and nhafi is the next-hop AFI. The pair lets an IPv4
                        route carry an IPv6 next hop, so an IPv6-only session can hold IPv4 reachability.";
                    ze:help "Extended Next Hop capability (RFC 8950)";
                    leaf family { type zt:address-family; description "Ze reads ipv4 and ipv6 as the AFI, and unicast, multicast, mpls-vpn and mpls-label as the SAFI. It skips
     an entry it cannot read.";
 ze:help "NLRI family (e.g. ipv4/unicast)"; }
                    leaf nhafi { type zt:afi; description "Ze reads ipv4 and ipv6 alone, and it skips an entry that names another value.";
 ze:help "Next-hop AFI (e.g. ipv6)"; }
                    leaf mode {
                        type capability-mode;
                        description "Ze takes the most restrictive mode over the whole list, where require wins against
                            refuse, and refuse wins against enable. enable and require both advertise the family.";
                        ze:help "Extended next hop negotiation mode";
                    }
                }
            }

        }

        // Behaviour container - operational knobs
        container behavior {
            description "Most operators can keep the defaults.";
            ze:help "Controls how the reactor processes and forwards an UPDATE for this peer.";

            leaf group-updates {
                type boolean;
                default true;
                description "Packing reduces the number of UPDATE messages from O(routes) to O(unique-attribute-sets). Disable it
                    for a peer that requires one prefix per UPDATE.";
                ze:help "Pack several NLRI into one UPDATE message when they share the same path attributes.";
            }

            leaf manual-eor {
                type boolean;
                description "When the leaf is enabled, End-of-RIB must be triggered from outside, through the process API. Use
                    the leaf when an external controller manages the convergence signaling.";
                ze:help "Do not send End-of-RIB automatically after the initial route advertisement.";
            }
        }

        container shutdown {
            presence "The peer is held administratively down";
            description "While the container is present Ze opens no session with the peer and answers an
                inbound connection with Cease subcode 5, Connection Rejected (RFC 4486 Section 4).
                'request peer <selector> enable' releases the hold until a commit adds or removes the
                container, and 'request peer <selector> disable' sets it again. A commit that adds the
                container to a peer whose session is up closes it with Cease subcode 2, Administrative
                Shutdown, carrying the message (RFC 9003 Section 2). A commit that removes it lets the
                peer connect.";
            ze:help "Hold the peer administratively down.";

            leaf message {
                type string;
                description "The RFC 9003 Shutdown Communication of the Cease a commit sends when it adds the
                    container to a peer whose session is up. Ze truncates it to the 255 octets the wire
                    carries.";
                ze:help "Shutdown communication sent with the Cease.";
            }
        }

        // Basic peer identification
        leaf description {
            type string;
            description "The CLI, the web UI, and the logs show the label. It usually names the role or the location of the
                peer, for example 'upstream-transit-provider'.";
            ze:help "Free-text label for this peer.";
        }

        container capture {
            description "When capture is enabled, Ze writes every message the peer sends to a JSONL file, as raw wire bytes
                with arrival metadata. The file also carries the config operations applied while the capture runs.
                Replay the file on a developer machine with 'le test replay <file>', which drives the same state
                machine over the same input. Capture is a diagnostic aid, so leave it off in steady state. The file
                holds the routing data of the peer: prefixes, AS paths, communities, and next hops. It holds no
                local secret, because a TCP-MD5 key never appears on the wire, and a captured config payload is
                redacted. Handle a capture file the way you handle a routing-table dump.";
            ze:help "Protocol event capture for this peer.";

            leaf enabled {
                type boolean;
                default false;
                description "When the leaf is true, Ze refuses the config if the directory is empty, and it refuses the
                    config if maximum-size is zero. Both refusals happen at config load, before the peer starts.";
                ze:help "Capture this peer's inbound protocol events to a file. Off by default.";
            }

            leaf directory {
                type string {
                    length "1..4096";
                }
                default "/var/lib/ze/capture";
                description "Ze creates the directory when it is absent. Ze writes one file per peer, named
                    bgp-<peer-address>.jsonl. Choose a filesystem with room for the configured maximum-size, and with
                    twice that room when on-limit is rotate. 'ze doctor' reports whether the directory is writable.";
                ze:help "Directory that holds the capture files of this peer.";
            }

            leaf maximum-size {
                type uint32 {
                    range "1..1024";
                }
                units megabytes;
                default 100;
                description "The writer refuses a record that would cross the cap, and it never writes part of a record, so a
                    file never exceeds this value. With on-limit rotate, a peer uses at most twice this value on disk.
                    With on-limit stop, a peer uses at most this value.";
                ze:help "Hard cap on the size of one capture file.";
            }

            leaf on-limit {
                type enumeration {
                    enum rotate { ze:help "Rename the full file to <file>.1 and start a fresh one, keeping the newest events."; }
                    enum stop { ze:help "Close the full file and capture nothing more, keeping the oldest events."; }
                }
                default rotate;
                description "'rotate' renames the file to <file>.1, which replaces any earlier rotation, and starts a fresh file.
                    Capture continues, and the newest events are kept. 'stop' closes the file and captures nothing more,
                    so the oldest events are kept. Either value leaves the daemon unaffected, and the file ends with a
                    capture-stop record.";
                ze:help "What happens when a capture file reaches maximum-size.";
            }
        }

        container timer {
            description "The speaker proposes the hold time in OPEN. The two peers negotiate it to the lower of their two
                values.";
            ze:help "BGP session timers: hold time, keepalive interval, and connect retry delay.";

            leaf receive-hold-time {
                type uint16 {
                    range "0 | 3..65535";
                }
                default 90;
                description "Ze puts the value in the Hold Time field of OPEN. The two peers then hold the lower of the
                    two values (RFC 4271 Section 4.2). Ze refuses 1 and 2, because the RFC permits 0, or 3 seconds
                    and more.";
                ze:help "Receive hold time in seconds (RFC 4271: 0 or >= 3). Proposed in OPEN.";
            }

            leaf send-hold-time {
                type uint16 {
                    range "0 | 480..65535";
                }
                default 0;
                description "RFC 9687 Section 4.4 requires a non-zero Send Hold Time to be more than the negotiated
                    hold time. Ze therefore refuses a value that is not more than receive-hold-time. Ze also
                    refuses a non-zero value of less than 480 seconds.";
                ze:help "Send hold time in seconds (RFC 9687). 0 = auto: max(480, 2x receive-hold-time).";
            }

            leaf keepalive {
                type uint16;
                default 0;
                description "Ze refuses a value that is not less than receive-hold-time, because the hold timer must be
                    able to detect a lost KEEPALIVE. 0 derives the interval from the negotiated hold time.";
                ze:help "Keepalive interval in seconds (RFC 4271 Section 10). 0 = auto: hold-time/3.";
            }

            leaf connect-retry {
                type uint16;
                default 120;
                description "Ze removes a disconnected dynamic peer after this delay when no connection comes back. A
                    static peer reconnects on an exponential backoff from 5 seconds to 60 seconds, and this leaf
                    does not change that backoff.";
                ze:help "Connect retry interval in seconds. Ze reads it for a dynamic peer alone.";
            }

            uses delay-open-timer;
        }

        uses update-block;

        // Process attachments
        container attach {
            ze:flatten;
            description "Each attachment names one program declared under plugin/external. It states what that program
                receives from this peer, and what the program can send to the peer. Write one statement per program:
                `attach process <name> { ... }`.";
            ze:help "Programs this peer attaches.";

            list process {
                key "name";
                description "Ze starts the process, and communicates with it over stdin and stdout, in JSON.";
                ze:help "External process that receives BGP events and can inject a message.";

                leaf name {
                    type string;
                    description "The name is the list key. An entry that also carries run declares an inline program
                        under this name, and Ze starts it. Ze declares one program per name, so the first entry
                        that carries run for a name wins.";
                    ze:help "Unique identifier for this process binding. Used in logs and status output.";
                }

                leaf run {
                    type string;
                    description "Ze pipes the BGP events to the stdin of the process, and reads the commands from its stdout.";
                    ze:help "Shell command that starts the external process.";
                }

                container content {
                    description "Ze reads encoding and format from the container. A binding that names neither takes
                        the encoder the program registered, and the parsed format.";
                    ze:help "Controls the encoding and filtering of events sent to this process.";
                    leaf encoding { type string; description "Ze resolves the value in three steps: this leaf first, then the default encoder the program registered,
     then text. Ze lowercases the value before it passes the value to the program binding.";
 ze:help "Wire encoding for events sent to the process (e.g., json, text)."; }
                    leaf format { type string; description "Ze uses parsed when the leaf is absent. Ze lowercases the value before it passes the value to the program
     binding.";
 ze:help "Output format template for event rendering."; }
                }

                leaf-list receive {
                    type string;
                    ze:validate "receive-event-type";
                    description "The base types are update, open, notification, keepalive, refresh, state, and negotiated. A plugin
                        registers more, for example update-rpki. A type carries the direction it is fed in: 'update' means
                        both directions, and 'update-received' and 'update-sent' each mean one direction. A registered type
                        keeps its whole name, so a plugin type that ends in -sent is never read as a direction. '*' feeds
                        every type, in both directions. 'all' is not accepted, because a word that reads like a type would
                        grant a type that a plugin registers later, which '*' says on purpose. Ze validates the list at
                        runtime against the registered event types.";
                    ze:help "Event types this peer feeds the program.";
                }

                leaf-list send {
                    type string;
                    ze:validate "send-message-type";
                    description "The valid types are update, refresh, raw, and enhanced-refresh. raw is a whole BGP message that the
                        program builds itself. enhanced-refresh carries the BORR and EORR markers of RFC 7313. '*' names
                        every type. A direction has no meaning here, because every send type is sent. Ze validates the list
                        at runtime against the known send types.";
                    ze:help "Message types this program can send toward the peer.";
                }
            }
        }

        // Filter chains
        container filter {
            description "A name references a filter instance defined under the top-level policy root.";
            ze:help "Route filter chains for import and export.";
            container import {
                presence "Configure an import policy.";
                description "Append these filters to inherited filters and use this policy's explicit final decision.";
                ze:help "Import policy";
                uses filter-policy;
            }
            container export {
                presence "Configure an export policy.";
                description "Append these filters to inherited filters and use this policy's explicit final decision.";
                ze:help "Export policy";
                uses filter-policy;
            }
        }

        // RIB configuration
        container rib {
            description "The container controls which RIB tables Ze maintains, and how the outbound route batching works.";
            ze:help "Route Information Base settings for this peer.";
            container adj {
                description "These tables hold the raw routes before policy and after policy. They make route-refresh and
                    soft-reconfiguration possible.";
                ze:help "Adjacency RIB storage for this peer.";
                leaf in {
                    type boolean;
                    description "The table makes inbound soft reconfiguration possible, which re-applies the import filters without a
                        session reset. It uses more memory, in proportion to the number of received routes.";
                    ze:help "Store received routes in Adj-RIB-In, before policy.";
                }
                leaf out {
                    type boolean;
                    description "Route-refresh (RFC 2918) needs the table to re-send the routes at the request of the peer. It uses
                        more memory, in proportion to the number of advertised routes.";
                    ze:help "Store advertised routes in Adj-RIB-Out, after policy.";
                }
            }
            container out {
                description "The three leaves act on the Adj-RIB-Out of this peer alone. They trade the number of
                    UPDATE messages and the CPU cost against the convergence latency.";
                ze:help "Outbound RIB batching: how route changes are grouped and flushed to the peer.";
                leaf group-updates {
                    type boolean;
                    default true;
                    description "The leaf does what the behavior-level group-updates does, for the Adj-RIB-Out of this peer alone.";
                    ze:help "Pack routes with identical attributes into one UPDATE.";
                }
                leaf auto-commit-delay {
                    type uint32;
                    default 0;
                    description "The delay batches rapid successive changes into fewer UPDATE messages. 0 flushes immediately on each
                        change.";
                    ze:help "Milliseconds to wait before Ze flushes pending route changes to the peer.";
                }
                leaf max-batch-size {
                    type int32;
                    default 0;
                    description "0 means no limit, so Ze flushes every pending change at once. A limit reduces the CPU cost of one
                        cycle, and raises the convergence latency.";
                    ze:help "Maximum number of route changes in one flush cycle.";
                }
            }
        }

    }

    // BGP-owned environment settings — augment hub's environment container
    augment "/hub:environment" {
        container bgp {
            description "The container controls the OPEN wait timeout and the initial announce delay.";
            ze:help "BGP protocol environment settings, applied before any peer-level config.";
            leaf openwait {
                type int32 { range "1..3600"; }
                default "120";
                description "The environment variable ze.bgp.openwait overrides the leaf. Ze arms the hold timer with
                    the value after it sends OPEN. Ze resets that timer to the negotiated hold time when the peer
                    OPEN arrives.";
                ze:help "Seconds to wait for peer OPEN after TCP connect";
            }
            leaf announce-delay {
                type string;
                default "0s";
                description "The environment variable ze.bgp.announce.delay overrides the leaf. Ze holds every peer
                    start for the delay after the reactor is otherwise Ready, which staggers route emission over a
                    restart.";
                ze:help "Delay between reactor Ready and first UPDATE (duration, 0s-1h)";
            }
        }

        container reactor {
            description "The reactor is the core event loop. It processes an incoming message, runs the peer FSMs, and
                dispatches an outbound UPDATE.";
            ze:help "BGP reactor engine tuning.";
            leaf speed { type string; default "1.0"; description "A value of less than 1.0 runs the loop faster, which lowers the latency and raises the CPU cost. A
     value of more than 1.0 runs the loop slower, which raises the latency and lowers the CPU cost.";
 ze:help "Reactor loop cycle time multiplier, from 0.1 to 10.0."; }
            leaf cache-ttl { type uint32; default 60; description "Ze reuses a cached UPDATE for a peer with the same encoding context, which removes a repeated
     serialization. 0 disables the cache, so Ze builds every UPDATE fresh.";
 ze:help "Seconds Ze keeps a built UPDATE wire message in the encoding cache."; }
            leaf cache-max { type uint32; default 1000000; description "The value bounds the memory that the encoding cache uses. 0 means unlimited, so the cache grows with
     the route table.";
 ze:help "Maximum number of cached UPDATE wire messages."; }
            leaf update-groups { type boolean; default true; description "The encoding context is the negotiated capabilities and the address families. Grouping reduces the
     CPU cost from O(peers x routes) to O(groups x routes). Disable it for debugging alone.";
 ze:help "Build each UPDATE once for every peer with the same encoding context."; }
            leaf forward-queue-size { type uint32 { range "1..1000000"; } default 256; description "The value is the number of UPDATE items Ze buffers for one destination peer before backpressure
     starts.";
 ze:help "Per-destination forward channel capacity."; }
            leaf forward-batch-limit { type uint32 { range "0..1000000"; } default 1024; description "The environment variable ze.fwd.batch.limit overrides the leaf. The limit bounds how long one drain holds
     the session write lock, so a large batch cannot block another writer for long.";
 ze:help "Max items per drain batch. Bounds writeMu hold time during forward dispatch. 0 means unlimited."; }
            leaf forward-pool-max-bytes { type uint32; default 0; description "The maximum is about 4GB. 0 means unlimited, and Ze then sizes the pools from the prefix maximums of
     the peers.";
 ze:help "Combined byte budget for the 4K and 64K buffer pools, in bytes."; }
            leaf forward-pool-headroom { type uint32; default 0; description "The maximum is about 4GB. Ze ignores the leaf when forward-pool-max-bytes is set explicitly.";
 ze:help "Extra bytes beyond the auto-sized pool baseline."; }
            leaf forward-teardown-grace { type string; default "5s"; description "The environment variable ze.fwd.teardown.grace overrides the leaf. Ze starts the period when the forward
     pool is more than 95% full and the peer holds more than twice its weight. A peer that does not drain inside
     the period is torn down.";
 ze:help "Grace period before forced teardown on congestion (duration string, e.g. 5s, 1m)."; }
            leaf read-buffer-size { type uint32 { range "4096..16777216"; } default 65536; description "The environment variable ze.buf.read.size overrides the leaf. Ze sizes one buffered reader per session at
     connection time, so a change reaches a session at its next connection. The kernel receive buffer is a separate
     256KB.";
 ze:help "Per-session TCP read buffer size in bytes."; }
            leaf write-buffer-size { type uint32 { range "4096..16777216"; } default 16384; description "The environment variable ze.buf.write.size overrides the leaf. A larger buffer packs more BGP messages
     into one write to the socket. The kernel send buffer is a separate 64KB.";
 ze:help "Per-session TCP write buffer size in bytes."; }
        }
    }
}
