module ze-loop-detection {
    namespace "urn:ze:loop-detection";
    prefix ld;

    import ze-policy-conf { prefix policy; }
    import ze-extensions { prefix ze; }
    import ze-types { prefix zt; }

    description "Loop detection filter type for the BGP policy framework.
                 Facade over the in-process LoopIngress wire-bytes filter.
                 RFC 4271 Section 9 (AS loop), RFC 4456 Section 8 (cluster-list loop).";

    revision 2026-04-09 {
        description "Initial revision";
    }

    augment "/policy:policy" {
        list loop-detection {
            ze:filter;
            key "name";
            description "The instance configures AS loop detection and cluster-list
                         loop detection, for each peer that references it.";
            ze:help "Named loop detection filter instance.";

            leaf name {
                type string;
                description "Ze puts the name at the front of the import chain of every peer that does not carry it.
                    An instance therefore applies with no chain edit. The first instance a peer chain names wins for
                    that peer. Write inactive:NAME in the chain to turn loop detection off for one peer.";
                ze:help "Filter instance name (referenced in peer filter chains)";
            }

            leaf allow-own-as {
                type uint8 {
                    range "0..10";
                }
                default 0;
                description "The default is 0, which rejects the route on the first
                             occurrence (RFC 4271 Section 9).";
                ze:help "Own-AS occurrences permitted in AS_PATH before ze rejects the route.";
            }

            leaf cluster-id {
                type zt:ipv4-address;
                description "When this leaf is unset, ze uses the BGP Router ID
                             (RFC 4456 Section 7).";
                ze:help "Override Router ID for CLUSTER_LIST loop detection.";
            }
        }
    }
}
