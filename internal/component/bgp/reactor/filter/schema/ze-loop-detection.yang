module ze-loop-detection {
    namespace "urn:ze:loop-detection";
    prefix ld;

    import ze-bgp-conf { prefix bgp; }
    import ze-extensions { prefix ze; }
    import ze-types { prefix zt; }

    description "Loop detection filter type for the BGP policy framework.
                 Facade over the in-process LoopIngress wire-bytes filter.
                 RFC 4271 Section 9 (AS loop), RFC 4456 Section 8 (cluster-list loop).";

    revision 2026-04-09 {
        description "Initial revision";
    }

    augment "/bgp:bgp/bgp:policy" {
        list loop-detection {
            ze:filter;
            key "name";
            description "Named loop detection filter instance.
                         Configures AS loop and cluster-list loop detection per-peer.";

            leaf name {
                type string;
                description "Filter instance name (referenced in peer filter chains)";
            }

            leaf allow-own-as {
                type uint8 {
                    range "0..10";
                }
                default 0;
                description "Number of own-AS occurrences to allow in AS_PATH before rejecting.
                             0 means reject on first occurrence (default, RFC 4271 Section 9).";
            }

            leaf cluster-id {
                type zt:ipv4-address;
                description "Override Router ID for CLUSTER_LIST loop detection.
                             If not set, uses the BGP Router ID (RFC 4456 Section 7).";
            }
        }
    }
}
