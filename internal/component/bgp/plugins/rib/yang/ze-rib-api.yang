module ze-rib-api {
    namespace "urn:ze:rib:api";
    prefix ribapi;

    import ze-types { prefix zt; }
    import ze-extensions { prefix ze; }

    description
        "RIB API operations for Ze.
         RPCs for querying and clearing RIB state.
         Notifications for RIB changes.";

    // Neither rpc reached a RIB command: the table in rib_commands.go holds
    // help, commands and events, and no entry answers either name. The live
    // pair is declared in ze-plugin-api.yang and ze-system-api.yang.
    revision 2026-09-13 {
        description "Removed command-help and command-complete.";
    }

    revision 2026-02-01 {
        description "Initial revision";
    }

    // RIB operations

    rpc status {
        description "The optional family argument scopes the per-peer route counts to one
address family. The routes-in and routes-out totals stay all-family counts whatever is
given.";
        ze:help "RIB summary: peer count, route counts, GR state.";
        output {
            leaf running {
                type boolean;
                description "Always true in an answer, because the plugin that answers is the
                             one that runs. A stopped plugin answers nothing.";
                ze:help "RIB plugin is running";
            }
            leaf peers {
                type uint32;
                description "The count of BGP peers whose session is up. A peer that is
                             configured and down is not counted.";
                ze:help "Number of peers tracked";
            }
            leaf routes-in {
                type uint32;
                description "The sum of the routes held in every Adj-RIB-In, over all address
                             families. The redistribution sources count as well as the BGP peers.";
                ze:help "Total Adj-RIB-In routes";
            }
            leaf routes-out {
                type uint32;
                description "The sum of the routes held in every Adj-RIB-Out, over all peers and
                             all address families.";
                ze:help "Total Adj-RIB-Out routes";
            }
            leaf stale-routes {
                type uint32;
                description "The count of Adj-RIB-In routes marked stale by graceful restart
                             (RFC 4724) and not yet refreshed by the restarted peer.";
                ze:help "Stale routes (GR)";
            }
        }
    }

    rpc show {
        description "The scope is sent, received, or sent-received, which is the default.
                     A filter is path <pattern>, prefix <pattern>, community <value>,
                     family <afi/safi>, or match <text>.
                     A terminal is one of four.
                     count returns metadata only.
                     json returns serialized output.
                     histogram returns the per-family prefix-length distribution.
                     graph returns the AS-path topology as box-drawing text.";
        ze:help "Show routes with pipeline filters.";
        input {
            leaf peer {
                type zt:ip-address;
                description "A peer selector. Given, only the routes received from or sent to the
                             matching peers are shown. Absent, every peer is shown.";
                ze:help "Filter by peer";
            }
            leaf-list args {
                type string;
                description "The words of the pipeline in order: an optional scope, then filters,
                             then one terminal. A keyword that is none of them is refused.";
                ze:help "Pipeline args: scope, filters, terminal";
            }
        }
        output {
            leaf route-count {
                type uint32;
                description "The count of routes the filters matched. It is answered when the
                             terminal is count, and the routes themselves are not.";
                ze:help "Number of routes (count terminal)";
            }
        }
    }

    rpc best {
        description "A filter is path <pattern>, prefix <pattern>, community <value>,
                     family <afi/safi>, or match <text>.
                     A terminal is one of four.
                     count returns metadata only.
                     json returns serialized output.
                     histogram returns the per-family prefix-length distribution.
                     graph returns the AS-path topology as box-drawing text.";
        ze:help "Show best-path per prefix (RFC 4271 §9.1.2).";
        input {
            leaf peer {
                type zt:ip-address;
                description "A peer selector. Given, only a best path learned from a matching peer
                             is shown. Absent, the best path of every prefix is shown.";
                ze:help "Filter by peer";
            }
            leaf-list args {
                type string;
                description "The words of the pipeline in order: filters, then one terminal. There
                             is no scope word, because a best path is always a received route.";
                ze:help "Pipeline args: filters, terminal";
            }
        }
        output {
            leaf route-count {
                type uint32;
                description "The count of prefixes with a best path that the filters matched. It
                             is answered when the terminal is count.";
                ze:help "Number of best paths";
            }
        }
    }

    rpc best-status {
        description "The peer count adds the BGP peers to the non-BGP redistribution sources
that feed the RIB. It can be larger than the BGP peer count, and the route count is the sum
over both.";
        ze:help "Show best-path computation status.";
        output {
            leaf peers-with-rib {
                type uint32;
                description "The count of sources that hold an Adj-RIB-In: the BGP peers plus the
                             non-BGP redistribution sources. A peer with an empty table counts.";
                ze:help "Peers with RIB entries";
            }
            leaf total-routes {
                type uint32;
                description "The sum of the routes held in those Adj-RIB-In tables, over all
                             address families. It counts received routes, not best paths.";
                ze:help "Total route count across peers";
            }
        }
    }

    rpc clear-in {
        description "A peer selector is required, and the command is refused without one. Each
matching peer loses its Adj-RIB-In and its entry in the peer table, and the best path is
then computed again.";
        ze:help "Clear Adj-RIB-In entries.";
        input {
            leaf peer {
                type zt:ip-address;
                description "A peer selector, one address or * for every peer. Each matching peer
                             loses its Adj-RIB-In. The selector is required.";
                ze:help "Filter by peer";
            }
            leaf family {
                type zt:address-family;
                description "An afi/safi pair, for example ipv4/unicast. The handler does not read
                             it: the Adj-RIB-In of a matching peer is cleared for every family.";
                ze:help "Filter by address family";
            }
        }
    }

    rpc clear-out {
        description "The routes are replayed and nothing is deleted. A peer selector is
required, and only a peer that is up is resent to. A second argument holding a slash scopes
the replay to one family.";
        ze:help "Resend the Adj-RIB-Out routes to the matching peers.";
        input {
            leaf peer {
                type zt:ip-address;
                description "A peer selector, one address or * for every peer. Each matching peer
                             that is up has its Adj-RIB-Out resent. The selector is required.";
                ze:help "Filter by peer";
            }
            leaf family {
                type zt:address-family;
                description "An afi/safi pair, for example ipv4/unicast. Given, only the routes of
                             that family are resent. Absent, every family is resent.";
                ze:help "Filter by address family";
            }
        }
    }

    rpc inject {
        description "The peer address is a label; no live BGP session required.";
        ze:help "Insert route into Adj-RIB-In as if received from a peer.";
        input {
            leaf peer {
                type zt:ip-address;
                mandatory true;
                description "The address the route is filed under in the Adj-RIB-In. A peer table
                             that does not exist yet is created, so no session is needed.";
                ze:help "Peer address label";
            }
            leaf family {
                type zt:address-family;
                mandatory true;
                description "An afi/safi pair. It selects the Adj-RIB-In table and the NLRI
                             encoding of the prefix.";
                ze:help "Address family (e.g. ipv4/unicast)";
            }
            leaf prefix {
                type string;
                mandatory true;
                description "The prefix in CIDR form, address and length. It is encoded as the
                             NLRI of the injected route.";
                ze:help "CIDR prefix (e.g. 10.0.0.0/24)";
            }
            leaf origin {
                type string;
                description "One of igp, egp and incomplete. Absent, the route carries igp. Any
                             other word is refused with the three names.";
                ze:help "Origin: igp, egp, incomplete (default: igp)";
            }
            leaf nhop {
                type zt:ip-address;
                description "An IPv4 value fills the NEXT_HOP attribute. An IPv6 value travels in
                             MP_REACH_NLRI, and for an IPv4 prefix the peer must have negotiated
                             extended-nexthop.";
                ze:help "Next-hop IP address";
            }
            leaf nexthop {
                type zt:ip-address;
                description "The same argument as nhop under its long spelling. Give one of the
                             two.";
                ze:help "Alias for nhop next-hop IP address";
            }
            leaf aspath {
                type string;
                description "The ASNs of the AS_PATH in order, separated by commas. Absent, the
                             path is empty.";
                ze:help "AS path as comma-separated ASNs (e.g. 64500,64501)";
            }
            leaf localpref {
                type uint32;
                description "An integer that fills the LOCAL_PREF attribute. Absent, the route
                             carries no LOCAL_PREF.";
                ze:help "LOCAL_PREF value";
            }
            leaf med {
                type uint32;
                description "An integer that fills the MULTI_EXIT_DISC attribute. Absent, the
                             route carries no MED.";
                ze:help "MULTI_EXIT_DISC value";
            }
        }
        output {
            leaf injected {
                type string;
                description "The prefix as it was given, echoed back once the route is in the
                             Adj-RIB-In and the best path is computed again.";
                ze:help "Prefix that was injected";
            }
            leaf peer {
                type zt:ip-address;
                description "The peer address the route was filed under, echoed as given.";
                ze:help "Peer the route was injected for";
            }
            leaf family {
                type zt:address-family;
                description "The afi/safi pair the route was filed under, echoed as given.";
                ze:help "Address family";
            }
        }
    }

    rpc withdraw {
        description "The peer, the family and the prefix are all required. The answer reports
whether the route existed, and the best path for that prefix is computed again.";
        ze:help "Remove route from Adj-RIB-In.";
        input {
            leaf peer {
                type zt:ip-address;
                mandatory true;
                description "The address the route is filed under in the Adj-RIB-In. A value that
                             is not an IP address is refused.";
                ze:help "Peer address label";
            }
            leaf family {
                type zt:address-family;
                mandatory true;
                description "An afi/safi pair. It selects the Adj-RIB-In table and the NLRI
                             encoding of the prefix.";
                ze:help "Address family";
            }
            leaf prefix {
                type string;
                mandatory true;
                description "The prefix in CIDR form, address and length. It is encoded as NLRI
                             and removed from the table when the encoding matches.";
                ze:help "CIDR prefix to withdraw";
            }
        }
        output {
            leaf withdrawn {
                type string;
                description "The prefix as it was given, echoed back once the best path for it
                             is computed again.";
                ze:help "Prefix that was withdrawn";
            }
            leaf peer {
                type zt:ip-address;
                description "The peer address the route was filed under, echoed as given.";
                ze:help "Peer the route was withdrawn from";
            }
            leaf family {
                type zt:address-family;
                description "The afi/safi pair the route was filed under, echoed as given.";
                ze:help "Address family";
            }
            leaf existed {
                type boolean;
                description "True when the table held the route and the withdraw removed it.
                             False when there was nothing to remove, which is not an error.";
                ze:help "Whether the route existed before withdrawal";
            }
        }
    }

    // Notifications

    notification rib-change {
        ze:method "ze-rib:rib-change";
        description "One event per peer and family whose table changed. It carries counts and
                     not the routes, so a subscriber reads the RIB for the detail.";
        ze:help "RIB content changed";
        leaf peer {
            type zt:ip-address;
            description "The address of the peer whose Adj-RIB-In changed.";
            ze:help "Affected peer";
        }
        leaf family {
            type zt:address-family;
            description "The afi/safi pair of the table that changed.";
            ze:help "Address family";
        }
        leaf added {
            type uint32;
            description "The count of routes the change inserted into the table.";
            ze:help "Routes added";
        }
        leaf removed {
            type uint32;
            description "The count of routes the change removed from the table.";
            ze:help "Routes removed";
        }
    }
}
