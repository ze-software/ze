module ze-healthcheck-conf {
    namespace "urn:ze:healthcheck-conf";
    prefix hc;

    import ze-bgp-conf { prefix bgp; }
    import ze-extensions { prefix ze; }

    description "BGP healthcheck plugin configuration for Ze";

    revision 2026-04-03 {
        description "Initial revision";
    }

    grouping probe-config {
        list probe {
            key "name";
            unique "group";
            description "A probe runs its command on a timer and holds its own state machine. The states are INIT,
                RISING, UP, FALLING, DOWN and DISABLED. Two probes cannot drive one watchdog group, because Ze
                refuses a config that repeats a group name.";
            ze:help "Healthcheck probe definition";

            leaf name {
                type string;
                description "The name is the list key. show bgp healthcheck NAME reports the state and the metrics of
                    one probe, and clear bgp healthcheck NAME restarts its state machine at INIT.";
                ze:help "Probe identifier";
            }

            leaf command {
                type string;
                mandatory true;
                description "Ze runs the command through /bin/sh -c. Exit 0 is a success, and every other exit status is
                    a failure. Ze reads at most 64 KB of the output of the command and writes it to the log.";
                ze:help "Shell command to execute for health check (exit 0 = success)";
            }

            leaf group {
                type string;
                mandatory true;
                description "The value matches the watchdog name of an update block. UP announces every route of the
                    group, and DOWN withdraws those routes or re-announces them with down-metric. Ze refuses a
                    second probe that names the same group. Ze also refuses the name med, and a name that holds a
                    space.";
                ze:help "Watchdog group name (exclusive: one probe per group)";
            }

            leaf interval {
                type uint32 {
                    range "0..86400";
                }
                default 5;
                description "The interval governs the UP, DOWN and DISABLED states. RISING and FALLING use fast-interval
                    instead. 0 runs one check, then the probe stays dormant until Ze stops it.";
                ze:help "Seconds between checks (0 = single check then dormant)";
            }

            leaf fast-interval {
                type uint32 {
                    range "1..3600";
                }
                default 1;
                description "RISING and FALLING are the states that count toward rise and fall, so the shorter interval
                    makes the probe reach UP or DOWN sooner. Every other state uses interval.";
                ze:help "Seconds between checks during RISING/FALLING states";
            }

            leaf timeout {
                type uint32 {
                    range "1..3600";
                }
                default 5;
                description "Ze kills the process group of the command with SIGKILL when the command runs longer than
                    the timeout. A killed command counts as a failure, so it advances the fall count.";
                ze:help "Command timeout in seconds";
            }

            leaf rise {
                type uint32 {
                    range "1..1000";
                }
                default 3;
                description "The probe counts successes in RISING and reaches UP at this count. One failure resets the
                    count to 1 and moves the probe to FALLING. The value 1 skips RISING, so the first success
                    reaches UP.";
                ze:help "Consecutive successes before UP";
            }

            leaf fall {
                type uint32 {
                    range "1..1000";
                }
                default 3;
                description "The probe counts failures in FALLING and reaches DOWN at this count. One success resets the
                    count to 1 and moves the probe to RISING. The value 1 skips FALLING, so the first failure
                    reaches DOWN.";
                ze:help "Consecutive failures before DOWN";
            }

            leaf withdraw-on-down {
                type boolean;
                default false;
                description "The default is false. Ze then keeps the route and re-announces it with down-metric, or with
                    disabled-metric.";
                ze:help "Withdraw the route when the probe is DOWN or DISABLED.";
            }

            leaf disable {
                type boolean;
                default false;
                description "Ze runs no check and skips the addresses of ip-setup at startup. The watchdog action for
                    DISABLED runs at once, so Ze withdraws the group or re-announces it with disabled-metric. clear
                    bgp healthcheck refuses a probe that carries true.";
                ze:help "Admin disable: probe enters DISABLED state immediately";
            }

            leaf debounce {
                type boolean;
                default false;
                description "The default false dispatches the watchdog command after every check, which re-announces the
                    same metric on each pass. true dispatches the command only when the state changes.";
                ze:help "When true, only dispatch watchdog commands on state changes";
            }

            leaf up-metric {
                type uint32;
                default 100;
                description "Ze runs request bgp watchdog announce GROUP med VALUE, so the value reaches every route of
                    the group as its MED attribute. A peer that compares two paths prefers the lower MED.";
                ze:help "MED value when UP";
            }

            leaf down-metric {
                type uint32;
                default 1000;
                description "The default 1000 is higher than the default up-metric of 100. A peer that holds a second
                    path therefore prefers that path while the probe is DOWN. withdraw-on-down true withdraws the
                    routes instead, and the value is then unused.";
                ze:help "MED value when DOWN (used when withdraw-on-down is false)";
            }

            leaf disabled-metric {
                type uint32;
                default 500;
                description "The default 500 sits between up-metric and down-metric, so a peer prefers a disabled box
                    over a failed one. withdraw-on-down true withdraws the routes instead, and the value is then
                    unused.";
                ze:help "MED value when DISABLED (used when withdraw-on-down is false)";
            }

            container ip-setup {
                description "Ze adds the addresses at startup, unless disable carries true, and removes every address it
                    added when the probe stops. The container does nothing until interface and ip both carry a
                    value.";
                ze:help "VIP management on local interface (internal plugin mode only)";

                leaf interface {
                    type string;
                    description "Ze resolves the logical interface name to its kernel device before it adds an address.
                        An empty leaf leaves the addresses of ip unused.";
                    ze:help "Target interface for VIPs (e.g., lo, dummy0)";
                }

                leaf dynamic {
                    type boolean;
                    default false;
                    description "The default false leaves the addresses on the interface for as long as the probe runs.
                        true removes them when the probe reaches DOWN or DISABLED, and adds them again on UP.";
                    ze:help "When true, remove IPs on DOWN/DISABLED, restore on UP";
                }

                leaf-list ip {
                    type string;
                    description "Ze records each address it added and removes only those, so an address another
                        component put on the interface stays. An address Ze fails to add is written to the log, and
                        the probe continues.";
                    ze:help "VIP addresses in CIDR notation (e.g., 10.0.0.1/32)";
                }
            }

            leaf-list on-up {
                type string;
                description "Ze runs the commands when the probe REACHES UP, and not on each later check that keeps it
                    there. The environment carries PATH, HOME, USER and STATE only, and STATE holds the state name.
                    Ze runs at most 10 hook commands at once.";
                ze:help "Shell commands to execute on transition to UP (30s timeout)";
            }

            leaf-list on-down {
                type string;
                description "Ze runs the commands when the probe REACHES DOWN, and not on each later check that keeps it
                    there. A failure of a hook command reaches the log and changes no state. The environment carries
                    PATH, HOME, USER and STATE only.";
                ze:help "Shell commands to execute on transition to DOWN (30s timeout)";
            }

            leaf-list on-disabled {
                type string;
                description "Ze reaches DISABLED from the disable leaf, never from a check result, so these commands run
                    at startup when disable is true. The environment carries PATH, HOME, USER and STATE only.";
                ze:help "Shell commands to execute on transition to DISABLED (30s timeout)";
            }

            leaf-list on-change {
                type string;
                description "STATE in the environment carries the name of the state the probe reached, so one command
                    CAN serve every transition. RISING and FALLING are transitions too, and they run these commands
                    with no state command of their own.";
                ze:help "Shell commands to execute on any state transition (30s timeout, runs after state-specific hooks)";
            }
        }
    }

    augment "/bgp:bgp" {
        container healthcheck {
            description "A probe runs a shell command on a timer and drives one watchdog group. The routes it controls
                are the update blocks whose watchdog name matches the group of the probe.";
            ze:help "Healthcheck probes for service-aware BGP route management";
            uses probe-config;
        }
    }
}
