module ze-flowspec-cmd {
    namespace "urn:ze:flowspec:cmd";
    prefix flowspeccmd;
    import ze-extensions       { prefix ze; }
    import ze-cli-announce-cmd { prefix cliannouncecmd; }
    // The components live here rather than in the announce module because this
    // plugin owns the vocabulary: parseComponentText dispatches on it and
    // isComponentKeyword is its single producer. The announce module must not
    // restate another plugin's words, and an augment means it does not have to.
    //
    // Every component is `repeat` rather than `once`. RFC 8955 Section 4.2
    // allows each component type exactly once, so a repeated keyword is another
    // OR group joined into the SAME component rather than a second one, which is
    // what AddComponent performs.
    //
    // Each container states `config false` itself. mergeYANGEntry skips a child
    // whose own Config is not false, and goyang sets Config from the node's own
    // statement with no propagation from the parent, so an augmented container
    // that omits it is dropped from the command tree without a word.
    description "The FlowSpec match components an operator types after `send bgp <selector> flowspec`.";
    // A prefix component names its family: RFC 8955 type 1 and RFC 8956 type 1
    // share a type code and carry different encodings, so destination-ipv4 and
    // destination-ipv6 are two names rather than one name and a qualifier. These
    // are the keywords ExaBGP emits. The bare words were its input aliases, and
    revision 2026-09-20 { description "traffic-class is declared beside dscp, so the text path takes the word the config path already took."; }
    revision 2026-09-05 { description "The augment names one path, send bgp <selector> flowspec. It named two while announce was reachable bare and under peer, and both are gone."; }
    // the ExaBGP bridge converts them now.
    revision 2026-08-31 { description "The bare destination and source keywords are removed."; }
    // The form answered at two paths when this grouping was written. It now
    // answers at one, send bgp <selector> flowspec, and the grouping stays
    // because an augment resolves against a grouping rather than a container.
    revision 2026-08-31 { description "announce flowspec is reachable at two paths, so the components became a grouping."; }
    // The model rather than a description states the grammar.
    revision 2026-08-30 { description "Initial revision: state the match components announce flowspec takes."; }

    grouping flowspec-components {
        // The augment below instantiates this grouping rather than restating
        // the vocabulary at the command's own path.
        description "The match components, declared once.";

        container destination-ipv4 {
            config false;
            ze:modifier "repeat";
            description "The prefix is parsed in CIDR form, and its address family MUST match the
FlowSpec family, so an IPv6 prefix under an IPv4 FlowSpec is refused. One NLRI
carries one destination prefix, so a second destination-ipv4 is refused as a
duplicate component type.";
            ze:help "Destination prefix to match (RFC 8955 type 1).";
            leaf prefix {
                type string { length "1..49"; }
                mandatory true;
                description "An IPv4 address and its prefix length, for example 192.0.2.0/24. The
packet's destination address must fall inside it.";
                ze:help "IPv4 prefix in CIDR form";
            }
        }

        container destination-ipv6 {
            config false;
            ze:modifier "repeat";
            description "The prefix is parsed in CIDR form, and it is refused when the FlowSpec family is
IPv4. RFC 8956 gives the IPv6 form an offset field that RFC 8955 has not, which
is why this keyword and destination-ipv4 are two words rather than one word and
a qualifier.";
            ze:help "Destination prefix to match (RFC 8956 type 1).";
            leaf prefix {
                type string { length "1..49"; }
                mandatory true;
                description "An IPv6 address and its prefix length, for example 2001:db8::/32.
The packet's destination address must fall inside it.";
                ze:help "IPv6 prefix in CIDR form";
            }
        }

        container source-ipv4 {
            config false;
            ze:modifier "repeat";
            description "The prefix is parsed in CIDR form, and its address family MUST match the
FlowSpec family, so an IPv6 prefix under an IPv4 FlowSpec is refused. One NLRI
carries one source prefix, so a second source-ipv4 is refused as a duplicate
component type.";
            ze:help "Source prefix to match (RFC 8955 type 2).";
            leaf prefix {
                type string { length "1..49"; }
                mandatory true;
                description "An IPv4 address and its prefix length, for example 198.51.100.0/24.
The packet's source address must fall inside it.";
                ze:help "IPv4 prefix in CIDR form";
            }
        }

        container source-ipv6 {
            config false;
            ze:modifier "repeat";
            description "The prefix is parsed in CIDR form, and it is refused when the FlowSpec family is
IPv4. One NLRI carries one source prefix, so a second source-ipv6 is refused as
a duplicate component type.";
            ze:help "Source prefix to match (RFC 8956 type 2).";
            leaf prefix {
                type string { length "1..49"; }
                mandatory true;
                description "An IPv6 address and its prefix length, for example 2001:db8:1::/48.
The packet's source address must fall inside it.";
                ze:help "IPv6 prefix in CIDR form";
            }
        }

        container protocol {
            config false;
            ze:modifier "repeat";
            description "A value is a name such as tcp, or a number from 0 to 255. A leading '=' is
accepted, so 'protocol =6' and 'protocol 6' parse the same way. Values are read
until the next component keyword, and each one is an equality match.";
            ze:help "IP protocol to match, by name or number (RFC 8955 type 3).";
            leaf value {
                type string { pattern '=?([0-9]+|[a-z0-9-]+)'; length "1..16"; }
                mandatory true;
                description "The IP protocol field, given as one of the names the parser knows or
as 0 to 255. Several values are read until the next component keyword.";
                ze:help "Protocol name such as tcp, or a number, optionally with a leading =";
            }
        }

        container next-header {
            config false;
            ze:modifier "repeat";
            description "A value is a name such as tcp, or a number from 0 to 255. This keyword and
'protocol' build the same component, and the two words exist because RFC 8956
names the IPv6 field Next Header. A leading '=' is accepted.";
            ze:help "IPv6 Next Header to match, by name or number (RFC 8956 type 3).";
            leaf value {
                type string { pattern '=?([0-9]+|[a-z0-9-]+)'; length "1..16"; }
                mandatory true;
                description "The IPv6 Next Header field, given as one of the names the parser
knows or as 0 to 255. Several values are read until the next component keyword.";
                ze:help "Header name such as tcp, or a number, optionally with a leading =";
            }
        }

        container port {
            config false;
            ze:modifier "repeat";
            description "A value takes an optional operator, one of '>=', '<=', '!=', '>', '<' and '='.
Without an operator the match is equality. The value is bounded at 65535. This
component matches either side of the flow, and destination-port and source-port
name one side each.";
            ze:help "Source or destination port to match (RFC 8955 type 4).";
            leaf value {
                type string { pattern '(>=|<=|!=|>|<|=)?(0[xX][0-9a-fA-F]+|[0-9]+)'; length "1..24"; }
                mandatory true;
                description "A transport port number, in decimal or as 0x hexadecimal. The
operator, when given, sits in front of the number with no space.";
                ze:help "Port, optionally with a comparison operator";
            }
        }

        container destination-port {
            config false;
            ze:modifier "repeat";
            description "A value takes an optional operator, one of '>=', '<=', '!=', '>', '<' and '='.
Without an operator the match is equality. The value is bounded at 65535. Use
'port' to match either side of the flow with one component.";
            ze:help "Destination port to match (RFC 8955 type 5).";
            leaf value {
                type string { pattern '(>=|<=|!=|>|<|=)?(0[xX][0-9a-fA-F]+|[0-9]+)'; length "1..24"; }
                mandatory true;
                description "The destination port number, in decimal or as 0x hexadecimal. The
operator, when given, sits in front of the number with no space.";
                ze:help "Port, optionally with a comparison operator";
            }
        }

        container source-port {
            config false;
            ze:modifier "repeat";
            description "A value takes an optional operator, one of '>=', '<=', '!=', '>', '<' and '='.
Without an operator the match is equality. The value is bounded at 65535. Use
'port' to match either side of the flow with one component.";
            ze:help "Source port to match (RFC 8955 type 6).";
            leaf value {
                type string { pattern '(>=|<=|!=|>|<|=)?(0[xX][0-9a-fA-F]+|[0-9]+)'; length "1..24"; }
                mandatory true;
                description "The source port number, in decimal or as 0x hexadecimal. The
operator, when given, sits in front of the number with no space.";
                ze:help "Port, optionally with a comparison operator";
            }
        }

        container icmp-type {
            config false;
            ze:modifier "repeat";
            description "A value takes an optional operator, one of '>=', '<=', '!=', '>', '<' and '='.
The value is bounded at 255. The ICMP type and the ICMP code are two components,
so pair this keyword with icmp-code when both MUST match.";
            ze:help "ICMP type to match (RFC 8955 type 7).";
            leaf value {
                type string { pattern '(>=|<=|!=|>|<|=)?(0[xX][0-9a-fA-F]+|[0-9]+)'; length "1..24"; }
                mandatory true;
                description "The ICMP type number, 0 to 255, in decimal or as 0x hexadecimal. The
operator, when given, sits in front of the number with no space.";
                ze:help "ICMP type, optionally with a comparison operator";
            }
        }

        container icmp-code {
            config false;
            ze:modifier "repeat";
            description "A value takes an optional operator, one of '>=', '<=', '!=', '>', '<' and '='.
The value is bounded at 255. This component carries no ICMP type, so pair it
with icmp-type when both MUST match.";
            ze:help "ICMP code to match (RFC 8955 type 8).";
            leaf value {
                type string { pattern '(>=|<=|!=|>|<|=)?(0[xX][0-9a-fA-F]+|[0-9]+)'; length "1..24"; }
                mandatory true;
                description "The ICMP code number, 0 to 255, in decimal or as 0x hexadecimal. The
operator, when given, sits in front of the number with no space.";
                ze:help "ICMP code, optionally with a comparison operator";
            }
        }

        container tcp-flags {
            config false;
            ze:modifier "repeat";
            description "A flag name is fin, syn, rst, psh, ack, urg, ece or cwr, and reset, push and
urgent are accepted aliases. A bitmask number is accepted in place of a name. A
leading '&' makes the term AND with the term before it, and without the '&' the
terms are OR.";
            ze:help "TCP flags to match (RFC 8955 type 9).";
            leaf value {
                type string { length "1..32"; }
                mandatory true;
                description "One term of the bitmask match. Flag names joined by '&' set several
bits in one term, a leading '!' negates the term, and a leading '=' asks for an exact
match of the mask.";
                ze:help "Flag name such as syn, or a bitmask, optionally with an operator";
            }
        }

        container packet-length {
            config false;
            ze:modifier "repeat";
            description "The length is the total IP packet length and it excludes the layer 2 header. A
value takes an optional operator, one of '>=', '<=', '!=', '>', '<' and '='. The
value is bounded at 65535.";
            ze:help "Packet length to match (RFC 8955 type 10).";
            leaf value {
                type string { pattern '(>=|<=|!=|>|<|=)?(0[xX][0-9a-fA-F]+|[0-9]+)'; length "1..24"; }
                mandatory true;
                description "The IP packet length in octets, in decimal or as 0x hexadecimal.
The operator, when given, sits in front of the number with no space.";
                ze:help "Length in octets, optionally with a comparison operator";
            }
        }

        container dscp {
            config false;
            ze:modifier "repeat";
            description "A value takes an optional operator, one of '>=', '<=', '!=', '>', '<' and '='.
The DSCP field is 6 bits, so the parser refuses a value over 63.";
            ze:help "DSCP value to match (RFC 8955 type 11).";
            leaf value {
                type string { pattern '(>=|<=|!=|>|<|=)?(0[xX][0-9a-fA-F]+|[0-9]+)'; length "1..24"; }
                mandatory true;
                description "The DSCP code point, 0 to 63, in decimal or as 0x hexadecimal. The
operator, when given, sits in front of the number with no space.";
                ze:help "DSCP, optionally with a comparison operator";
            }
        }

        container traffic-class {
            config false;
            ze:modifier "repeat";
            description "The word ExaBGP writes for the container above. RFC 8956 Section 8 registers
component type 11 under one name for both families, so Ze writes dscp and accepts this word beside it.
A value takes an optional operator, one of '>=', '<=', '!=', '>', '<' and '='.";
            ze:help "DSCP value to match, under the ExaBGP spelling.";
            leaf value {
                type string { pattern '(>=|<=|!=|>|<|=)?(0[xX][0-9a-fA-F]+|[0-9]+)'; length "1..24"; }
                mandatory true;
                description "The DSCP code point, 0 to 63, in decimal or as 0x hexadecimal. The
operator, when given, sits in front of the number with no space.";
                ze:help "DSCP, optionally with a comparison operator";
            }
        }

        container fragment {
            config false;
            ze:modifier "repeat";
            description "A flag name is dont-fragment, is-fragment, first-fragment or last-fragment, and
df, isf, ff and lf are accepted aliases. A leading '&' makes the term AND with
the term before it. RFC 8955 Section 4.2.2.12 defines the four bits.";
            ze:help "Fragment bits to match (RFC 8955 type 12).";
            leaf value {
                type string { length "1..32"; }
                mandatory true;
                description "One term of the bitmask match. Names joined by '&' set several bits
in one term, a leading '!' negates the term, and a leading '=' asks for an exact match
of the mask.";
                ze:help "Fragment name such as is-fragment, or a bitmask";
            }
        }

        container flow-label {
            config false;
            ze:modifier "repeat";
            description "The IPv6 Flow Label is a 20-bit field, and RFC 8956 defines this component for
IPv6 FlowSpec alone. A value takes an optional operator, one of '>=', '<=',
'!=', '>', '<' and '='. The parser bounds the value at 32 bits.";
            ze:help "IPv6 Flow Label to match (RFC 8956 type 13).";
            leaf value {
                type string { pattern '(>=|<=|!=|>|<|=)?(0[xX][0-9a-fA-F]+|[0-9]+)'; length "1..24"; }
                mandatory true;
                description "The Flow Label value, in decimal or as 0x hexadecimal. The operator,
when given, sits in front of the number with no space.";
                ze:help "Flow label, optionally with a comparison operator";
            }
        }

        container rd {
            config false;
            ze:modifier "once";
            description "This is the one component declared 'once' rather than 'repeat'. The encoder
removes the rd pair before it walks the other components, so an rd that reaches
the walk names a family carrying no Route Distinguisher and is refused. Write
the value as ASN:value or as address:value.";
            ze:help "Route Distinguisher, for a VPN FlowSpec family only.";
            leaf value {
                type string { length "1..32"; }
                mandatory true;
                description "The Route Distinguisher the VPN NLRI carries in front of its
components. A value the RD parser cannot read is refused with its own message.";
                ze:help "Route Distinguisher, as ASN:value or address:value";
            }
        }
    }

    // One augment, because the form answers at one path. It carried two while
    // announce was reachable bare and under peer, and both of those are gone.
    // A path this augment cannot resolve makes every config load fail, so the
    // path here and the container in ze-cli-announce-cmd move together.
    augment "/cliannouncecmd:send/cliannouncecmd:bgp/cliannouncecmd:flowspec" {
        uses flowspec-components;
    }
}
