module ze-filter-modify {
    namespace "urn:ze:filter-modify";
    prefix fm;

    import ze-policy-conf { prefix policy; }
    import ze-extensions { prefix ze; }
    import ze-types { prefix zt; }

    description "Route attribute modifier for the BGP policy framework.
                 Named modifier definitions with attribute operations.
                 A modifier applies the declared operations to every route that
                 reaches it or, when it states a match condition, only to the
                 routes that meet it. Routes that do not meet the condition pass
                 through unchanged.
                 Referenced from peer filter chains as modify:NAME.";

    revision 2026-10-30 {
        description
          "Add the route source conditions (protocol, tag, level, route-type) to
           match and the Loc-RIB sets distance and tag to set, so one modifier
           type serves the Loc-RIB import chains beside the BGP chains.";
    }
    revision 2026-08-15 {
        description
          "Add del med. RFC 4271 Section 5.1.4 requires a speaker to
           implement a mechanism, based on local configuration, that allows
           MULTI_EXIT_DISC to be removed from a route. Previously, med was a
           set target only, while removal was available only for the three
           community attributes.";
    }

    revision 2026-08-13 {
        description
          "Add the match container. A filter chain is a pipe in which a reject
           DROPS the route, so a match filter placed earlier can only express
           'modify these and discard the rest'. A route that must keep flowing
           untouched had nowhere to go. This is what lets a community select an
           action: a next-hop rewrite toward a discard address on a route
           carrying an operator's blackhole community, RFC 7999 among them,
           while every other route from the same peer forwards normally.";
    }

    revision 2026-05-25 {
        description "Add increment/decrement containers and community add/remove leaf-lists";
    }

    augment "/policy:policy" {
        list modify {
            ze:filter;
            key "name";
            description "Ze modifies only the declared leaves, and keeps every undeclared
attribute unchanged. One modifier can change several attributes.";
            ze:help "Named route attribute modifier instance.";

            leaf name {
                type string;
                description "A peer filter chain names this instance as modify:NAME, where
NAME is the value of this leaf.";
                ze:help "Modifier instance name, used in a peer filter chain.";
            }

            container match {
                description "A route that meets none of the stated values passes through
unchanged, and Ze does not reject it. The chain drops a rejected route, and a
conditional modifier exists so that the routes it does not touch keep flowing. An
absent match container applies the operations to every route that reaches the modifier.
The values across the three leaf-lists are alternatives, so one value present in the
route satisfies the condition.";
                ze:help "Condition a route meets before the operations apply.";

                leaf-list community {
                    type string;
                    description "The COMMUNITIES attribute is RFC 1997, type 8. The value takes
the form ASN:VAL, for example 65001:666, or a well-known name. The well-known names are
blackhole, no-export, no-advertise, no-export-subconfed and nopeer. The two spellings
of a well-known value are equivalent, so 65535:666 and blackhole select the same
community. RFC 7999 registers that community, and RFC 7999 Section 4 names it with that
suggested keyword.";
                    ze:help "Apply only to a route whose COMMUNITIES attribute carries this value.";
                }

                leaf-list large-community {
                    type string;
                    description "The LARGE COMMUNITIES attribute is RFC 8092, type 32. The value
takes the form GA:LD1:LD2, for example 65001:100:200. Ze validates the value at
configure time and compares its canonical decimal form.";
                    ze:help "Apply only to a route whose LARGE COMMUNITIES attribute carries this value.";
                }

                leaf-list extended-community {
                    type string;
                    description "The EXTENDED COMMUNITIES attribute is RFC 4360, type 16. The
value takes the form target:ASN:NN or origin:ASN:NN, or it is a hex string. Ze
validates the value at configure time and compares its eight-octet value, so named
and hex spellings of the same value select the same routes.";
                    ze:help "Apply only to a route whose EXTENDED COMMUNITIES attribute carries this value.";
                }
                uses policy:route-source-conditions {
                    description "These conditions read where a route came from, which only a Loc-RIB
route carries: an instance naming one runs on a Loc-RIB import chain (isis, ospf,
static, connected, rib filter import) and is refused on a BGP chain. Each one named
must hold, beside the community alternatives.";
                }
            }

            container set {
                description "Ze applies only the leaves that are present in this container,
and keeps every other attribute unchanged.";
                ze:help "Attributes Ze sets on a matching route.";

                leaf local-preference {
                    type uint32;
                    description "Ze replaces the value the route carried. RFC 4271 Section 5.1.5 forbids the attribute
                        in an UPDATE to an external peer, so the value serves the local decision process and the
                        internal peers. The leaf is mutually exclusive with increment local-preference and decrement
                        local-preference.";
                    ze:help "Set LOCAL_PREF attribute (RFC 4271 type 5).";
                }

                leaf med {
                    type uint32;
                    description "Ze replaces the metric the route carried, and writes one on a route that carried none.
                        The leaf is mutually exclusive with del med, increment med and decrement med, and Ze refuses
                        a modifier that carries two of them.";
                    ze:help "Set MULTI_EXIT_DISC attribute (RFC 4271 type 4).";
                }

                leaf origin {
                    type enumeration {
                        enum igp {
                            ze:help "The route started inside the local AS.";
                        }
                        enum egp {
                            ze:help "The route came from the retired EGP protocol.";
                        }
                        enum incomplete {
                            ze:help "The route came from another source, such as redistribution.";
                        }
                    }
                    description "The decision process reads the attribute at step 3, after LOCAL_PREF and the AS_PATH
                        length. igp wins over egp, and egp wins over incomplete. Ze replaces whatever the route
                        carried.";
                    ze:help "Set ORIGIN attribute (RFC 4271 type 1).";
                }

                leaf next-hop {
                    type zt:ip-address;
                    description "NEXT_HOP is RFC 4271 type 3, and it carries an IPv4 address
only. An IPv6 next-hop travels in the MP_REACH attribute instead, which this leaf does
not set, so an IPv6 address here is refused when the config is read.";
                    ze:help "Set the NEXT_HOP attribute of the route.";
                }

                leaf as-path-prepend {
                    type uint8 {
                        range "1..32";
                    }
                    description "Ze prepends the local-as of the peer, which the session config
holds. The range 1 to 32 stops the path from growing without a limit.";
                    ze:help "Prepend the local AS to AS_PATH this many times.";
                }

                leaf-list community-add {
                    type string;
                    description "Ze adds the values to the COMMUNITIES attribute of RFC 1997 and keeps every community
                        already on the route. Ze reads each value at config load, and refuses the modifier when one
                        does not parse.";
                    ze:help "Standard community values to add (ASN:VAL format).";
                }

                leaf-list community-remove {
                    type string;
                    description "Ze removes only the values named here, and keeps every other community of the route.
                        A value the route does not carry costs nothing. Ze reads each value at config load, and
                        refuses the modifier when one does not parse.";
                    ze:help "Standard community values to remove (ASN:VAL format).";
                }

                leaf-list large-community-add {
                    type string;
                    description "The LARGE COMMUNITIES attribute is RFC 8092, type 32, and it carries three 4-byte
                        fields. A 4-byte ASN therefore fits, which a standard community cannot hold.";
                    ze:help "Large community values to add (GA:LD1:LD2 format).";
                }

                leaf-list large-community-remove {
                    type string;
                    description "Ze removes only the values named here, and leaves the standard and extended communities
                        of the route untouched. A value the route does not carry costs nothing.";
                    ze:help "Large community values to remove (GA:LD1:LD2 format).";
                }

                leaf-list extended-community-add {
                    type string;
                    description "The EXTENDED COMMUNITIES attribute is RFC 4360, type 16, and each value is 8 bytes.
                        target names a Route Target and origin names a Route Origin. A hex string writes the 8 bytes
                        Ze has no keyword for.";
                    ze:help "Extended community values to add (target:ASN:NN or hex).";
                }

                leaf-list extended-community-remove {
                    type string;
                    description "Ze removes only the values named here, and leaves the standard and large communities of
                        the route untouched. A value the route does not carry costs nothing.";
                    ze:help "Extended community values to remove (target:ASN:NN or hex).";
                }
                leaf distance {
                    type uint8;
                    description "Ze ranks a matching route at this administrative distance in the Loc-RIB,
in place of the distance declared for its protocol. A Loc-RIB import chain only: the
instance is refused on a BGP chain. Removing the filter returns the route to the
declared distance.";
                    ze:help "Set the administrative distance of a Loc-RIB route (0-255).";
                }
                leaf tag {
                    type uint32;
                    description "Ze replaces the route's tag in the Loc-RIB with this value. A Loc-RIB
import chain only: the instance is refused on a BGP chain.";
                    ze:help "Set the tag of a Loc-RIB route.";
                }
                leaf metric {
                    type uint32 { range "0..16777215"; }
                    description "Ze advertises a matching route with this metric: the prefix metric of
an IS-IS export, the metric of an OSPF AS-external LSA, whose field is 24 bits wide. An
IGP export chain only: the instance is refused at any attachment that does not let a
filter set the metric.";
                    ze:help "Set the metric an IGP export advertises (0-16777215).";
                }
                leaf metric-type {
                    type enumeration {
                        enum type-1 { ze:help "External metric in OSPF cost units, added to the internal distance."; }
                        enum type-2 { ze:help "External metric larger than any internal path, compared alone."; }
                    }
                    description "RFC 2328 section 2.3 states that a Type 1 external metric is in the
same units as the OSPF cost, and a Type 2 metric is larger than any internal path. An
OSPF export chain only. A route no filter sets takes type-2.";
                    ze:help "Set the OSPF external metric type of an exported route.";
                }
            }

            container del {
                description "Ze applies only the leaves that are present in this container,
and keeps every other attribute unchanged.";
                ze:help "Attributes Ze deletes from a matching route.";

                leaf med {
                    type empty;
                    description "RFC 4271 Section 5.1.4 requires a mechanism, based on local
configuration, that removes MULTI_EXIT_DISC from a route. The same section requires the
removal to happen before the route reaches Decision Process phase 1 and phase 2. The
del med operation is that mechanism, so it applies on an IMPORT chain only, and the
route enters the decision process with no metric. Ze refuses del med on an export chain
and writes a log line, because Section 9.1.2.2 states that a comparison on
MULTI_EXIT_DISC followed by advertisement without it causes route loops. del med is
mutually exclusive with set med, increment med and decrement med. Ze already keeps a
metric received from one neighboring AS off another one with no configuration (RFC 4271
Section 5.1.4), so del med is for the operator who wants the metric removed from the
route itself.";
                    ze:help "Remove the MULTI_EXIT_DISC attribute (RFC 4271 type 4) from the route.";
                }
            }

            container increment {
                description "Ze adds the stated value to the current value of the attribute.
The result saturates at the uint32 maximum, 4294967295. increment is mutually exclusive
with set for the same attribute.";
                ze:help "Attributes to increment on a matching route.";

                leaf local-preference {
                    type uint32 {
                        range "1..4294967295";
                    }
                    description "A route that carries no LOCAL_PREF counts as 100, which is the value FRR and BIRD use
                        for a route with none. RFC 4271 Section 9.1.1 leaves that number to local policy.";
                    ze:help "Increment LOCAL_PREF by this value.";
                }

                leaf med {
                    type uint32 {
                        range "1..4294967295";
                    }
                    description "A route that carries no MULTI_EXIT_DISC counts as 0, which RFC 4271 Section 9.1.2.2
                        gives as the value of an absent metric. The result therefore equals the increment.";
                    ze:help "Increment MED by this value.";
                }

                leaf aigp {
                    type uint32 {
                        range "1..4294967295";
                    }
                    description "Ze runs the operation only on a route that already carries an AIGP TLV, and creates
                        none. RFC 7311 Section 3.4.1 forbids a speaker to add the attribute to a route whose path
                        leaves the AIGP domain. Section 4.1 removes a route with no AIGP from the decision rather
                        than scoring it.";
                    ze:help "Increment AIGP metric by this value.";
                }
            }

            container decrement {
                description "Ze subtracts the stated value from the current value of the
attribute. The result floors at 0, so it never underflows. decrement is mutually
exclusive with set for the same attribute.";
                ze:help "Attributes to decrement on a matching route.";

                leaf local-preference {
                    type uint32 {
                        range "1..4294967295";
                    }
                    description "A route that carries no LOCAL_PREF counts as 100 before the subtraction. A decrement
                        larger than the current value writes 0 rather than wrapping.";
                    ze:help "Decrement LOCAL_PREF by this value.";
                }

                leaf med {
                    type uint32 {
                        range "1..4294967295";
                    }
                    description "A route that carries no MULTI_EXIT_DISC counts as 0, so the result is 0 and Ze writes a
                        metric the route did not have. Use del med to remove the attribute instead.";
                    ze:help "Decrement MED by this value.";
                }

                leaf aigp {
                    type uint32 {
                        range "1..4294967295";
                    }
                    description "Ze runs the operation only on a route that already carries an AIGP TLV. A route with
                        none is left alone, because RFC 7311 Section 3.4.1 forbids Ze to add the attribute.";
                    ze:help "Decrement AIGP metric by this value.";
                }
            }
        }
    }
}
