module ze-filter-modify {
    namespace "urn:ze:filter-modify";
    prefix fm;

    import ze-bgp-conf { prefix bgp; }
    import ze-extensions { prefix ze; }
    import ze-types { prefix zt; }

    description "Route attribute modifier for the BGP policy framework.
                 Named modifier definitions with attribute setters.
                 Each modifier unconditionally sets the declared attributes
                 on routes that reach it in the filter chain. For conditional
                 modification, compose with match filters (prefix-list,
                 as-path-list, community-match) earlier in the chain.
                 Referenced from peer filter chains as modify:NAME.";

    revision 2026-05-25 {
        description "Add increment/decrement containers and community add/remove leaf-lists";
    }

    augment "/bgp:bgp/bgp:policy" {
        list modify {
            ze:filter;
            key "name";
            description "Named route attribute modifier instance.
                         Only declared leaves are modified; undeclared
                         attributes are preserved unchanged. Multiple
                         attributes can be set in a single modifier.";

            leaf name {
                type string;
                description "Modifier instance name (referenced in peer filter
                             chains as modify:NAME).";
            }

            container set {
                description "Attributes to set on matching routes.
                             Only present leaves are applied.";

                leaf local-preference {
                    type uint32;
                    description "Set LOCAL_PREF attribute (RFC 4271 type 5).";
                }

                leaf med {
                    type uint32;
                    description "Set MULTI_EXIT_DISC attribute (RFC 4271 type 4).";
                }

                leaf origin {
                    type enumeration {
                        enum igp {
                            description "IGP origin";
                        }
                        enum egp {
                            description "EGP origin";
                        }
                        enum incomplete {
                            description "Incomplete origin";
                        }
                    }
                    description "Set ORIGIN attribute (RFC 4271 type 1).";
                }

                leaf next-hop {
                    type zt:ip-address;
                    description "Set NEXT_HOP attribute (RFC 4271 type 3).
                                 IPv4 address only (IPv6 next-hop is in MP_REACH).";
                }

                leaf as-path-prepend {
                    type uint8 {
                        range "1..32";
                    }
                    description "Prepend local AS to AS_PATH this many times.
                                 The actual ASN prepended is the peer's local-as
                                 (from session config). Range 1-32 prevents
                                 excessive path inflation.";
                }

                leaf-list community-add {
                    type string;
                    description "Standard community values to add (ASN:VAL format).";
                }

                leaf-list community-remove {
                    type string;
                    description "Standard community values to remove (ASN:VAL format).";
                }

                leaf-list large-community-add {
                    type string;
                    description "Large community values to add (GA:LD1:LD2 format).";
                }

                leaf-list large-community-remove {
                    type string;
                    description "Large community values to remove (GA:LD1:LD2 format).";
                }

                leaf-list extended-community-add {
                    type string;
                    description "Extended community values to add (target:ASN:NN or hex).";
                }

                leaf-list extended-community-remove {
                    type string;
                    description "Extended community values to remove (target:ASN:NN or hex).";
                }
            }

            container increment {
                description "Attributes to increment on matching routes.
                             Adds the specified value to the current attribute
                             value. Saturates at uint32 max (4294967295).
                             Mutually exclusive with set for the same attribute.";

                leaf local-preference {
                    type uint32 {
                        range "1..4294967295";
                    }
                    description "Increment LOCAL_PREF by this value.";
                }

                leaf med {
                    type uint32 {
                        range "1..4294967295";
                    }
                    description "Increment MED by this value.";
                }

                leaf aigp {
                    type uint32 {
                        range "1..4294967295";
                    }
                    description "Increment AIGP metric by this value.";
                }
            }

            container decrement {
                description "Attributes to decrement on matching routes.
                             Subtracts the specified value from the current
                             attribute value. Floors at 0 (no underflow).
                             Mutually exclusive with set for the same attribute.";

                leaf local-preference {
                    type uint32 {
                        range "1..4294967295";
                    }
                    description "Decrement LOCAL_PREF by this value.";
                }

                leaf med {
                    type uint32 {
                        range "1..4294967295";
                    }
                    description "Decrement MED by this value.";
                }

                leaf aigp {
                    type uint32 {
                        range "1..4294967295";
                    }
                    description "Decrement AIGP metric by this value.";
                }
            }
        }
    }
}
