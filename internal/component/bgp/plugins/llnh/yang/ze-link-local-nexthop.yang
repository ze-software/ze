module ze-link-local-nexthop {
    namespace "urn:ze:link-local-nexthop";
    prefix llnh;

    import ze-bgp-conf { prefix bgp; }
    import ze-extensions { prefix ze; }

    description
        "Link-local next-hop capability plugin for Ze
         (draft-ietf-idr-linklocal-capability, code 77).
         Signals peer support for IPv6 link-local addresses as BGP next-hops.";

    revision 2025-02-08 {
        description "Initial revision.";
    }

    grouping link-local-nexthop-config {
        leaf link-local-nexthop {
            type enumeration {
                enum enable { ze:help "Advertise the capability"; }
                enum disable { ze:help "Do not advertise the capability, overriding the group"; }
            }
            description
                "The capability advertises that ze accepts IPv6 link-local
                 next-hops in MP_REACH_NLRI (RFC 2545 Section 3).
                 Requires session link-local on the peer or its group:
                 the configuration is refused without it, because ze must
                 send its own link-local address once the capability is
                 negotiated (draft-ietf-idr-linklocal-capability Section 4).
                 Only enable and disable: the plugin enforces neither
                 require nor refuse, so the schema does not offer them.
                 A peer's value overrides its group's; absent on both
                 means not advertised.";
            ze:help
                "Link-local next-hop capability: enable or disable.";
        }
    }

    // Standalone peer capability
    augment "/bgp:bgp/bgp:peer/bgp:session/bgp:capability" {
        uses link-local-nexthop-config;
    }

    // Peer inside group capability
    augment "/bgp:bgp/bgp:group/bgp:peer/bgp:session/bgp:capability" {
        uses link-local-nexthop-config;
    }

    // Group-level capability
    augment "/bgp:bgp/bgp:group/bgp:session/bgp:capability" {
        uses link-local-nexthop-config;
    }
}
