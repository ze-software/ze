module ze-rs-conf {
    namespace "urn:ze:rs:conf";
    prefix rs;

    import ze-bgp-conf { prefix bgp; }
    import ze-extensions { prefix ze; }

    description "BGP route server plugin configuration for Ze";

    revision 2026-07-04 {
        description "Adopt the rs-client (session) and rs-fast-path (behavior)
                     per-peer leaves from core ze-bgp-conf so the route-server
                     config surface is plugin-owned: removing this plugin removes
                     the leaves from the schema.";
    }

    revision 2026-06-12 {
        description "Initial revision";
    }

    augment "/bgp:bgp" {
        container route-server {
            description "The route server forwards an UPDATE from one client to every other client. Each source peer
                gets its own worker, and the worker stops after 5 seconds with no work. A peer joins the client set
                with the rs-client leaf of its session, not with this container.";
            ze:help "Route server plugin tuning parameters";

            leaf worker-queue-size {
                type uint32 {
                    range "1..1000000";
                }
                default 4096;
                description "Per-source-peer worker channel capacity. The ze.bgp.route-server.worker-queue-size environment
                    variable overrides this value.";
                ze:help "Worker channel capacity per source peer, overridden by ze.bgp.route-server.worker-queue-size.";
            }
        }
    }

    // Per-peer route-server session leaf, adopted from core ze-bgp-conf so the
    // route-server config surface is plugin-owned (delete this plugin and the
    // leaf vanishes from the schema). The reactor still parses it from the
    // merged session container -- it owns the PeerSettings field the leaf drives.
    grouping rs-session-config {
        leaf rs-client {
            type boolean;
            default false;
            description "Mark this peer as an RS-client for transparent AS-path forwarding. RFC 7947 Section 2.2.2: the route
                server MUST NOT modify AS_PATH or any other transitive attribute. When this leaf is true, the
                reactor skips AS-path prepending for this peer on the forwarding path.";
            ze:help "Mark this peer as an RS-client for transparent AS-path forwarding.";
        }
    }

    // Per-peer route-server behavior leaf, adopted from core ze-bgp-conf (see
    // rs-session-config). Enables the reactor RS fast-path forwarding for the peer;
    // the fast path itself is gated on this plugin activating the capability.
    grouping rs-behavior-config {
        leaf rs-fast-path {
            type boolean;
            default false;
            description "Forward received UPDATEs directly inside the reactor for RS-client peers, and bypass the plugin
                dispatch chain. This path gives lower latency for route server forwarding. A peer with an export
                filter is excluded and uses the normal path. The fast path obeys the route server's attach grants:
                it forwards only from a peer that attaches this plugin with receive [ update-received ], and only
                to a peer that attaches it with send [ update ]. Add both to every rs-fast-path peer:
                attach process <route-server> { receive [ update-received ]; send [ update ]; }.";
            ze:help "Forward an RS-client UPDATE inside the reactor. Needs the route server's update grants.";
        }
    }

    augment "/bgp:bgp/bgp:peer/bgp:session"           { uses rs-session-config; }
    augment "/bgp:bgp/bgp:group/bgp:peer/bgp:session" { uses rs-session-config; }
    augment "/bgp:bgp/bgp:group/bgp:session"          { uses rs-session-config; }

    augment "/bgp:bgp/bgp:peer/bgp:behavior"           { uses rs-behavior-config; }
    augment "/bgp:bgp/bgp:group/bgp:peer/bgp:behavior" { uses rs-behavior-config; }
    augment "/bgp:bgp/bgp:group/bgp:behavior"          { uses rs-behavior-config; }
}
