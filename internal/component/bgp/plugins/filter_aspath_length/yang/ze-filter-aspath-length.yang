module ze-filter-aspath-length {
    namespace "urn:ze:filter-aspath-length";
    prefix fal;

    import ze-policy-conf { prefix policy; }
    import ze-extensions { prefix ze; }

    description "AS-path length filter type for the BGP policy framework.
                 Named filters that accept or reject routes based on AS_PATH
                 hop count. Ze counts every ASN of the path, so a member of an
                 AS_SET and an ASN of a confederation segment each count as one
                 hop. That count is the filter's own, and it is not the length
                 the decision process of RFC 4271 Section 9.1.2.2 compares.
                 Referenced from peer filter chains as as-path-length:NAME.";

    revision 2026-05-25 {
        description "Initial revision";
    }

    augment "/policy:policy/policy:match" {
        description "The as-path-length condition of a match instance: the AS-path length filter
                     registers it, so a build without BGP has no such condition.";
        leaf as-path-length {
            type string { length "1..max"; }
            ze:reference "policy-as-path-length";
            description "The UPDATE passes this condition when its AS path hop count lies within the
                         named as-path-length instance's min and max. The editor completes the
                         configured as-path-length instances, and a commit naming any other is
                         refused. Only a BGP chain judges it.";
            ze:help "Match routes whose AS path length the named as-path-length allows";
        }
    }

    augment "/policy:policy" {
        list as-path-length {
            ze:filter;
            key "name";
            description "Ze rejects a route whose AS-path length falls outside the
                         configured min..max range. Both min and max are optional,
                         and an omitted bound is open.";
            ze:help "Named AS-path length filter instance.";

            leaf name {
                type string;
                description "The filter answers accept or reject for the whole UPDATE, and never rewrites it. A chain
                    that names a filter Ze does not hold rejects every route of that peer.";
                ze:help "Filter instance name (referenced in peer filter
                         chains as as-path-length:NAME).";
            }

            leaf max {
                type uint16 {
                    range "1..65535";
                }
                description "An absent leaf leaves the upper bound open, so a filter that states neither bound accepts
                    every route. Ze counts every ASN of the path, so a member of an AS_SET counts as one hop.";
                ze:help "Maximum allowed AS-path length (inclusive).
                         Routes with longer paths are rejected.";
            }

            leaf min {
                type uint16 {
                    range "0..65535";
                }
                description "An absent leaf leaves the lower bound open. A route that carries no AS_PATH counts 0
                    hops. min 1 therefore rejects a route Ze originated, and a route an iBGP peer sent with an
                    empty path.";
                ze:help "Minimum required AS-path length (inclusive).
                         Routes with shorter paths are rejected.";
            }
        }
    }
}
