module ze-filter-remove-private-as {
    namespace "urn:ze:filter-remove-private-as";
    prefix frpa;

    import ze-policy-conf { prefix policy; }
    import ze-extensions { prefix ze; }

    description "Remove Private Use ASNs from AS_PATH and AS4_PATH in the BGP policy framework.
                 Referenced from peer filter chains as remove-private-as:NAME.";

    revision 2026-05-24 {
        description "Initial revision";
    }

    augment "/policy:policy" {
        list remove-private-as {
            ze:filter;
            key "name";
            description "Ze rewrites AS_PATH and AS4_PATH, and the filter runs on an import chain and on an export
                chain. A path that carries no Private Use ASN passes through unchanged.";
            ze:help "Named action filter that removes RFC 6996 Private Use ASNs.";

            leaf name {
                type string;
                description "A peer filter chain names this instance as remove-private-as:NAME. A chain that names an
                    instance Ze does not hold rejects every route of that peer, because the filter fails closed.";
                ze:help "Filter instance name.";
            }

            leaf replace-with {
                type enumeration {
                    enum peer-as {
                        ze:help "Replace Private Use ASNs with the neighbor peer ASN.";
                    }
                }
                description "RFC 6996 Section 5 gives the ranges, which are 64512 to 65534 and 4200000000 to
                    4294967294. An absent leaf strips each of those ASNs, so the path loses one hop for each.
                    peer-as writes the ASN of the peer in its place, so the path keeps its length.";
                ze:help "Replacement mode. When absent, Private Use ASNs are stripped.";
            }
        }
    }
}
