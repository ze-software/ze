module ze-filter-family {
    namespace "urn:ze:filter-family";
    prefix ff;

    import ze-policy-conf { prefix policy; }
    import ze-extensions { prefix ze; }
    import ze-types { prefix zt; }

    description "Address-family policy filter for ZeBGP. Matches an AFI/SAFI in a
                 BGP UPDATE and either removes that family's NLRI (import + export)
                 or tears down the session (import only). Referenced from peer
                 filter chains as bgp-filter-family:NAME.";

    revision 2026-06-26 {
        description "Initial revision";
    }

    augment "/policy:policy" {
        list family-filter {
            ze:filter;
            key "name";
            description "One instance matches one family, because family holds one value and is mandatory. A chain that
                must catch two families names two instances.";
            ze:help "Named address-family filter instance.";

            leaf name {
                type string;
                description "A peer filter chain names this instance as bgp-filter-family:NAME,
where NAME is the value of this leaf.";
                ze:help "Filter instance name, used in a peer filter chain.";
            }

            leaf family {
                type zt:address-family;
                mandatory true;
                description "Ze treats an UPDATE with no MP_REACH attribute and no MP_UNREACH
attribute as ipv4/unicast.";
                ze:help "Address family to match, for example ipv4/flowspec.";
            }

            leaf action {
                type enumeration {
                    enum remove {
                        ze:help "Strip the MP_REACH NLRI and the MP_UNREACH NLRI of the matched family.";
                    }
                    enum tear-down {
                        ze:help "Close the session with a BGP NOTIFICATION when a received UPDATE carries the family.";
                    }
                }
                mandatory true;
                description "remove strips the MP_REACH NLRI and the MP_UNREACH NLRI of the
matched family from the UPDATE, on import and on export. If that removal empties the
UPDATE, Ze drops the whole UPDATE for that peer.

tear-down sends a BGP NOTIFICATION that carries the Cease code and the Connection
Rejected subcode, then closes the session. tear-down acts on import only.";
                ze:help "Action to apply when the family matches.";
            }
        }
    }
}
