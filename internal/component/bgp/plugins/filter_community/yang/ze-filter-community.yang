module ze-filter-community {
    namespace "urn:ze:filter-community";
    prefix fc;

    import ze-bgp-conf { prefix bgp; }
    import ze-extensions { prefix ze; }

    description "Community filter plugin for ZeBGP — tag/strip communities on ingress/egress";

    revision 2026-08-12 {
        description
          "Ingress leaves for RFC 8195 Section 3.2 relation tagging, RFC 7454
           Section 11 own-Global-Administrator scrub, and RFC 7999 Section 3.2
           blackhole propagation guard. All sit inside community-filter-fields, so
           the four existing augment sites carry them with no new augment.";
    }

    revision 2026-03-27 {
        description "Initial revision";
    }

    // Named community definitions under bgp { community { } }
    augment "/bgp:bgp" {
        container community {
            description "A filter rule names a set from this container rather than
                         repeating the community values. The three lists hold standard,
                         large and extended communities.";
            ze:help "Named community definitions referenced by filter rules.";

            list standard {
                key "name";
                description "Each entry holds one or more ASN:value pairs under one name.
                             An ingress or egress tag or strip list names the entry
                             in place of the values. Ze refuses a set that holds no
                             value. It refuses a name a second entry of the
                             standard, large or extended list already holds. It
                             refuses a tag or a strip list that names a set no
                             entry declares.";
                ze:help "Named sets of standard communities a tag or a strip list names.";
                leaf name {
                    type string;
                    description "The name is the list key, and a filter rule names this
                                 set by it.";
                    ze:help "Community set name.";
                }

                leaf-list value {
                    type string;
                    description "A standard community is two 16-bit numbers, written
                                 ASN:value (RFC 1997).";
                    ze:help "Standard community values, in ASN:value format.";
                }
            }

            list large {
                key "name";
                description "Each entry holds one or more GA:LD1:LD2 triples under one name.
                             An ingress or egress tag or strip list names the entry
                             in place of the values. Ze refuses a set that holds no
                             value. It refuses a name a second entry of the
                             standard, large or extended list already holds. It
                             refuses a tag or a strip list that names a set no
                             entry declares.";
                ze:help "Named sets of large communities a tag or a strip list names.";
                leaf name {
                    type string;
                    description "The name is the list key, and a filter rule names this
                                 set by it.";
                    ze:help "Community set name.";
                }

                leaf-list value {
                    type string;
                    description "A large community is three 32-bit numbers, written
                                 GA:LD1:LD2 (RFC 8092).";
                    ze:help "Large community values, in GA:LD1:LD2 format.";
                }
            }

            list extended {
                key "name";
                description "Each entry holds one or more extended community values under one name.
                             An ingress or egress tag or strip list names the entry
                             in place of the values. Ze refuses a set that holds no
                             value. It refuses a name a second entry of the
                             standard, large or extended list already holds. It
                             refuses a tag or a strip list that names a set no
                             entry declares.";
                ze:help "Named sets of extended communities a tag or a strip list names.";
                leaf name {
                    type string;
                    description "The name is the list key, and a filter rule names this
                                 set by it.";
                    ze:help "Community set name.";
                }

                leaf-list value {
                    type string;
                    description "An extended community is eight octets, and its type
                                 decides how Ze reads the value (RFC 4360).";
                    ze:help "Extended community values.";
                }
            }
        }
    }

    // Community filter config grouping — ingress/egress community tag/strip.
    // Augmented into the existing filter container at bgp, group, and peer levels.
    grouping community-filter-fields {
        container ingress {
            description "The container holds the filters Ze runs over a route it receives
                         from this peer.";
            ze:help "Ingress direction filters.";

            container community {
                description "The container holds the tag list, the strip list, and the
                             RFC 8195, RFC 7454 and RFC 7999 leaves.";
                ze:help "Community filter for ingress.";

                leaf-list tag {
                    type string;
                    ze:cumulative;
                    description "Each value names a set in the bgp community container.
                                 Ze adds every community of that set to the route.";
                    ze:help "Named communities to add on ingress.";
                }

                leaf-list strip {
                    type string;
                    ze:cumulative;
                    description "Each value names a set in the bgp community container.
                                 Ze removes every community of that set from the route.";
                    ze:help "Named communities to remove on ingress.";
                }

                leaf relation-tag {
                    type boolean;
                    default "false";
                    description
                      "RFC 8195 Section 3.2 defines the community. The Global
                       Administrator is the session local AS. The parameter comes
                       from what the peer IS to us: 2 for a customer, 3 for a
                       peer, 4 for a provider. A route-server session and a
                       route-server-client session write nothing, because RFC 7947
                       requires transparency there. An iBGP session writes nothing.
                       Its sender is inside the local AS and has no such
                       relation.";

                    ze:help
                      "Write the relation-to-origin large community of RFC 8195 on each route from this peer.";
                }

                leaf relation-function {
                    type uint32;
                    default 3;
                    description
                      "RFC 8195 Section 3.2 leaves this number to each AS and gives
                       3 as its example. The number is a local convention, not a
                       protocol constant. Change it here when the AS already uses 3
                       for something else.";
                    ze:help
                      "Function number of the relation tag.";
                }

                leaf scrub-own-ga {
                    type boolean;
                    default "false";
                    description
                      "Only the function numbers listed in scrub-keep-function
                       survive. RFC 7454 Section 11 asks for the scrub. It covers
                       standard and large communities. It runs on eBGP sessions
                       only. On an iBGP session an own-AS value is this network's
                       own signal to itself. Well-known communities are never
                       reached, so NO_EXPORT, NO_ADVERTISE and BLACKHOLE always
                       survive.";
                    ze:help
                      "Remove inbound communities whose Global Administrator is the local AS.";
                }

                leaf-list scrub-keep-function {
                    type uint32;
                    ze:cumulative;
                    description
                      "The list is RFC 7454 Section 11's exception for what
                       customers and peers use to signal. An empty list keeps

                       nothing. The relation-tag function number is never kept,
                       whatever this list says: a kept relation function would let
                       a peer state its own relation to this AS.";
                    ze:help
                      "Function numbers a peer can send with the local AS as the Global Administrator.";
                }

                leaf blackhole-propagation {
                    type enumeration {
                        enum none {
                            ze:help "Add nothing. RFC 7999 Section 3.1 makes ignoring the community conformant.";
                        }
                        enum no-export {
                            ze:help "Add NO_EXPORT (65535:65281).";
                        }
                        enum no-advertise {
                            ze:help "Add NO_ADVERTISE (65535:65282).";
                        }
                    }
                    default "none";
                    description
                      "The community stops the prefix propagating outside the local
                       AS, which RFC 7999 Section 3.2 asks for. The choice between
                       the two values is the operator routing policy, so neither is
                       forced. This leaf adds the community. It does not discard
                       traffic.";
                    ze:help
                      "Community to add to a route that carries BLACKHOLE (65535:666).";

                }
            }
        }

        container egress {
            description "The container holds the filters Ze runs over a route it sends to
                         this peer.";
            ze:help "Egress direction filters.";

            container community {
                description "The container holds the tag list and the strip list.";
                ze:help "Community filter for egress.";

                leaf-list tag {
                    type string;
                    ze:cumulative;
                    description "Each value names a set in the bgp community container.
                                 Ze adds every community of that set to the route.";
                    ze:help "Named communities to add on egress.";
                }

                leaf-list strip {
                    type string;
                    ze:cumulative;
                    description "Each value names a set in the bgp community container.
                                 Ze removes every community of that set from the route.";
                    ze:help "Named communities to remove on egress.";
                }
            }
        }
    }

    // Standalone peer — augment existing filter container
    augment "/bgp:bgp/bgp:peer/bgp:filter" {
        uses community-filter-fields;
    }

    // Peer inside group — augment existing filter container
    augment "/bgp:bgp/bgp:group/bgp:peer/bgp:filter" {
        uses community-filter-fields;
    }

    // Group-level — augment existing filter container
    augment "/bgp:bgp/bgp:group/bgp:filter" {
        uses community-filter-fields;
    }

    // BGP-level (global defaults) — augment existing filter container
    augment "/bgp:bgp/bgp:filter" {
        uses community-filter-fields;
    }
}
