module ze-filter-prefix {
    namespace "urn:ze:filter-prefix";
    prefix fp;

    import ze-policy-conf { prefix policy; }
    import ze-extensions { prefix ze; }
    import ze-types { prefix zt; }

    description "Prefix-list filter type for the BGP policy framework.
                 Named prefix-lists with ordered match entries (first match wins),
                 ge/le length ranges, and accept/reject actions.
                 Referenced from peer filter chains as bgp-filter-prefix:NAME.";

    revision 2026-04-11 {
        description "Initial revision";
    }

    augment "/policy:policy/policy:match" {
        description "The prefix-list condition of a match instance: the prefix filter registers
                     it, so a build without BGP has no such condition.";
        leaf prefix-list {
            type string { length "1..max"; }
            ze:reference "policy-prefix-list";
            description "The route passes this condition when the named prefix-list accepts its prefix.
                         The prefix-list is a policy prefix-list instance: the editor completes the
                         configured ones, and a commit naming any other is refused.";
            ze:help "Match routes the named prefix-list accepts";
        }
    }

    augment "/policy:policy" {
        list prefix-list {
            ze:filter;
            key "name";
            description "Each list holds an ordered set of match entries. Ze evaluates
                         the entries in order, and the first match wins. A route prefix
                         that matches no entry is denied.";
            ze:help "Named prefix-list filter instance.";

            leaf name {
                type string;
                description "A chain that names a list Ze does not hold rejects every route of that peer, because the
                    filter fails closed. The same happens for an UPDATE that arrives before the config reached the
                    plugin.";
                ze:help "Filter instance name (referenced in peer filter chains
                         as bgp-filter-prefix:NAME).";
            }

            list entry {
                key "prefix";
                ordered-by user;
                description "Ze judges each prefix of an UPDATE on its own. An UPDATE whose prefixes are all accepted
                    passes unchanged, and one whose prefixes are all rejected is dropped. A mixed UPDATE is
                    rewritten to carry the accepted prefixes only. An UPDATE that carries no prefix is accepted.";
                ze:help "Ordered match entry. First match wins per route prefix.";

                leaf prefix {
                    type union {
                        type zt:prefix-ipv4;
                        type zt:prefix-ipv6;
                    }
                    description "The prefix is the list key, so one entry holds one prefix and its length window. The
                        length of the prefix is the lower bound of that window until ge moves it. A prefix Ze cannot
                        parse rejects the UPDATE.";
                    ze:help "IPv4 or IPv6 CIDR prefix to match.
                             Match requires the route prefix be a subnet of this prefix.";
                }

                leaf ge {
                    type uint8 {
                        range "0..128";
                    }
                    description "Ze refuses a value of more than 32 on an IPv4 entry, and more than 128 on an IPv6
                        entry. Ze also refuses a ge greater than the le of the same entry. Write 0.0.0.0/0 with ge 8
                        and le 24 to accept every route between /8 and /24.";
                    ze:help "Minimum match length (greater-than-or-equal).
                             Defaults to the prefix length of this entry.";
                }

                leaf le {
                    type uint8 {
                        range "0..128";
                    }
                    description "The default accepts every length inside the entry, so an entry with no le and no ge
                        matches the prefix and everything under it. Ze refuses a value greater than the family
                        maximum rather than letting the entry match nothing.";
                    ze:help "Maximum match length (less-than-or-equal).
                             Defaults to 32 for IPv4 or 128 for IPv6.";
                }

                leaf action {
                    type enumeration {
                        enum accept {
                            ze:help "Accept route prefixes matching this entry.";
                        }
                        enum reject {
                            ze:help "Reject route prefixes matching this entry.";

                        }
                    }
                    default accept;
                    description "The first entry that matches a route prefix decides it, and no later entry is read for
                        that prefix. A prefix that matches no entry is rejected, so a list needs no closing reject
                        entry.";
                    ze:help "Action applied when this entry matches a route prefix.";
                }
            }
        }
    }
}
