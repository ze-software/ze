module ze-filter-irr-cmd {
    namespace "urn:ze:filter-irr:cmd";
    prefix firrcmd;
    import ze-extensions { prefix ze; }
    description "show bgp irr ... and update bgp irr ... command tree. Owned by the bgp-filter-irr plugin so that removing the IRR filter surface removes these command nodes together with the handlers and config schema. See ai/rules/plugin-self-containment.md.";
    revision 2026-06-14 { description "Initial revision."; }

    container show {
        config false;
        ze:help "Read-only commands to inspect system, protocol, and network state.";

        container bgp {
            config false;
            description "Typed with no subcommand, lists every peer with state, ASN,
prefixes received, and uptime. Optionally scope by address family: ipv4, ipv6,
or l2vpn.";
            ze:help "BGP peers, sessions, RIB, and protocol tools.";

            container irr {
                config false;
                ze:command "ze-bgp:show-irr-status";
                description "Lists each enrolled ASN with its resolved AS-SET, prefix counts,
last refresh time, and error status. Use this to confirm that IRR
prefix-lists are loaded and current.";
                ze:help "Show IRR filter status per ASN.";

                container prefix {
                    config false;
                    ze:command "ze-bgp:show-irr-prefix";
                    description "Lists all IPv4 and IPv6 prefixes
in the IRR-resolved prefix-list for the given peer address.";
                    ze:help "Show IRR-resolved prefixes for a peer.";
                    leaf peer {
                        type string;
                        mandatory true;
                        description "The address of an IRR-filtered peer, spelled as the configuration
spells it. The plugin finds the ASN the peer is enrolled under and answers that ASN's
prefix list. An address no enrolled ASN carries is refused.";
                        ze:help "Peer address.";
                    }
                }

                container check {
                    config false;
                    ze:command "ze-bgp:show-irr-check";
                    description "Reports whether the
prefix would be accepted or rejected, and which entry matches.";
                    ze:help "Check if a prefix is accepted by the IRR filter.";
                    leaf peer {
                        type string;
                        mandatory true;
                        description "The address of an IRR-filtered peer, spelled as the configuration
spells it. The prefix is evaluated against the list of the ASN that peer is enrolled
under. An address no enrolled ASN carries is refused.";
                        ze:help "Peer address.";
                    }
                    leaf prefix {
                        type string;
                        mandatory true;
                        description "An IPv4 or IPv6 prefix in CIDR form, which Ze parses before the
check. The answer echoes it and reports accepted true or false, with the entry that
matched when one did.";
                        ze:help "Prefix to check (CIDR).";
                    }
                }
            }
        }
    }

    container update {
        config false;

        container bgp {
            config false;
            ze:help "BGP operational updates.";

            container irr {
                config false;
                description "The fetch reaches an external IRR database over the network, so it can fail for a
                             reason unrelated to BGP. A failed refresh keeps the previous prefix list rather
                             than emptying it, so no route is accidentally accepted.";
                ze:help "IRR prefix-list refresh commands.";

                container all {
                    config false;
                    ze:command "ze-bgp:update-irr-all";
                    description "Re-queries the IRR server for every enrolled ASN and atomically
swaps prefix-lists on success. Failed refreshes preserve the
existing prefix-list and report an error.";
                    ze:help "Refresh all IRR prefix-lists immediately.";
                }

                container asn {
                    config false;
                    ze:command "ze-bgp:update-irr-asn";
                    description "Re-queries the IRR server for
the given ASN only.";
                    ze:help "Refresh IRR prefix-list for a specific ASN.";
                    leaf asn {
                        type string;
                        mandatory true;
                        description "The AS number as a plain decimal from 0 to 4294967295. An ASN with
no IRR-filtered peer is refused, and a refresh the IRR server fails is reported with the
server's error.";
                        ze:help "ASN number.";
                    }
                }

                container as-set {
                    config false;
                    ze:command "ze-bgp:update-irr-as-set";
                    description "Re-queries the IRR server
for all peers using the given AS-SET name.";
                    ze:help "Refresh IRR prefix-list for a specific AS-SET.";
                    leaf as-set {
                        type string;
                        mandatory true;
                        description "The AS-SET name as the peer configuration spells it, compared as an
exact string. Every enrolled ASN that resolves through this AS-SET is refreshed, and a
name no enrolled ASN uses is refused.";
                        ze:help "AS-SET name.";
                    }
                }
            }
        }
    }
}
