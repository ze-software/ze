module ze-filter-irr {
    namespace "urn:ze:filter-irr";
    prefix firr;

    import ze-bgp-conf { prefix bgp; }
    import ze-policy-conf { prefix policy; }
    import ze-types { prefix zt; }
    import ze-extensions { prefix ze; }

    description "IRR-based prefix-list filter for eBGP peers.
                 Queries IRR databases for AS-SET prefixes and applies them
                 as import filters. Referenced from peer filter chains as
                 bgp-filter-irr:$remote_as.";

    revision 2026-06-13 {
        description "Initial revision";
    }

    grouping irr-peer-config {
        container irr {
            description "Ze resolves the prefixes of a peer only when the peer asked for it. A filter chain that names
                bgp-filter-irr asks for it, and so does an as-set written here. A peer that states no remote ASN is
                never resolved.";
            ze:help "Per-peer IRR filter settings.";

            leaf as-set {
                type string;
                description "The IRR filter queries an IRR database for the prefixes of one AS-SET.
This leaf names that AS-SET. If this leaf is empty, Ze reads the remote ASN of the
peer and discovers the AS-SET from PeeringDB.";
                ze:help "Explicit AS-SET name for the IRR prefix lookup.";
            }

            leaf enable {
                type enumeration {
                    enum enable {
                        ze:help "Enable IRR filtering for this peer (default).";
                    }
                    enum disable {
                        ze:help "Disable IRR filtering for this peer.";
                    }
                }
                default "enable";
                description "disable takes the peer out of the resolution, so Ze runs no whois query and no PeeringDB
                    query for it. The other peers of the same remote ASN keep their list.";
                ze:help "Enable or disable IRR filtering for this peer.";
            }
        }
    }

    augment "/policy:policy" {
        container irr {
            description "The container holds the IRR server, the PeeringDB endpoint and the refresh period. One
                resolution serves every peer of the same remote ASN, so two peers of one ASN cost one query.";
            ze:help "Global IRR filtering settings.";

            leaf server {
                type string;
                default "whois.radb.net";
                description "Ze speaks whois to the server and adds port 43 when the value carries no port. A query that
                    gets no answer in 10 seconds fails, and the prefix list of the last query stays in force.";
                ze:help "IRR whois server hostname or host:port.";
            }

            leaf peeringdb-url {
                type string {
                    pattern 'https?://.*';
                }
                default "https://www.peeringdb.com";
                description "Ze reads the AS-SET of a peer from the PeeringDB API when the
as-set leaf is empty. Set this leaf to the URL of a mock server to test the IRR filter
without a query to the public PeeringDB service.";
                ze:help "Base URL of the PeeringDB API that Ze queries.";
            }

            leaf source-address {
                type zt:ip-address;
                description "Ze binds the address on the whois connection only. The PeeringDB query does not read the
                    leaf. When the leaf is absent, the kernel picks the source address of the route to the server.";
                ze:help "Source IP address for outbound IRR whois connections.";
            }

            leaf refresh-interval {
                type uint32 {
                    range "60..86400";
                }
                default "3600";
                units "seconds";
                description "Ze re-queries every enrolled AS-SET on this period. The first query runs in the background
                    at startup, so a slow IRR server never blocks the start of Ze. A failed query leaves the prefix
                    list of the last query in force.";
                ze:help "Seconds between automatic IRR re-queries.";
            }
        }
    }

    augment "/bgp:bgp/bgp:peer/bgp:session" {
        uses irr-peer-config;
    }

    augment "/bgp:bgp/bgp:group/bgp:peer/bgp:session" {
        uses irr-peer-config;
    }

    augment "/bgp:bgp/bgp:group/bgp:session" {
        uses irr-peer-config;
    }
}
