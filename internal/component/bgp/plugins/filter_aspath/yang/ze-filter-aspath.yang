module ze-filter-aspath {
    namespace "urn:ze:filter-aspath";
    prefix fa;

    import ze-policy-conf { prefix policy; }
    import ze-extensions { prefix ze; }

    description "AS-path regex filter type for the BGP policy framework.
                 Named as-path-lists with ordered regex entries (first match wins)
                 and accept/reject actions. The AS-path is converted to a
                 space-separated decimal string (e.g. '65001 65002 65003') and
                 each entry's regex is matched against it using Go RE2 semantics
                 (linear time, no backtracking -- inherently ReDoS-safe).
                 Referenced from peer filter chains as bgp-filter-aspath:NAME.";

    revision 2026-04-12 {
        description "Initial revision";
    }

    augment "/policy:policy/policy:match" {
        description "The as-path condition of a match instance: the AS-path filter registers
                     it, so a build without BGP has no such condition.";
        leaf as-path {
            type string { length "1..max"; }
            ze:reference "policy-as-path-list";
            description "The UPDATE passes this condition when the named as-path-list accepts its AS path,
                         read as the space-separated decimal string. The as-path-list is a policy
                         as-path-list instance: the editor completes the configured ones, and a commit
                         naming any other is refused. Only a BGP chain judges it.";
            ze:help "Match routes whose AS path the named as-path-list accepts";
        }
    }

    augment "/policy:policy" {
        list as-path-list {
            ze:filter;
            key "name";
            description "Each list holds an ordered set of regex entries. Ze evaluates the
entries in order, and the first match wins. No match is an implicit deny, so Ze rejects
the route.";
            ze:help "Named AS-path regex filter instance.";

            leaf name {
                type string;
                description "A peer filter chain references this instance as
bgp-filter-aspath:NAME or as as-path-list:NAME.";
                ze:help "Filter instance name, referenced in a peer filter chain.";
            }

            list entry {
                key "regex";
                ordered-by user;
                description "Ze matches each entry against the space-separated AS-path string,
in the configured order. The first entry that matches wins.";
                ze:help "One regex entry of the ordered list.";

                leaf regex {
                    type string;
                    description "Ze builds the AS-path string from the decimal ASNs, with one
space between them. '^65001$' matches one AS exactly. '^65001 ' matches a path that
starts with AS 65001. '^$' matches an empty AS-path, which is a locally originated
route. The syntax is Go RE2, which guarantees linear time. The maximum length is 512
characters.";
                    ze:help "Regular expression matched against the decimal AS-path string.";
                }

                leaf action {
                    type enumeration {
                        enum accept {
                            ze:help "Accept a route whose AS-path matches.";
                        }
                        enum reject {
                            ze:help "Reject a route whose AS-path matches.";
                        }
                    }
                    default accept;
                    description "The first entry whose pattern matches decides the UPDATE, and no later entry is read. A
                        route whose path matches no entry is rejected, so a list needs no closing reject entry.";
                    ze:help "Action applied when this entry's regex matches.";
                }
            }
        }
    }
}
