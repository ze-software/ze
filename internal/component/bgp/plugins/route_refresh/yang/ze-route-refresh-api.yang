module ze-route-refresh-api {
    namespace "urn:ze:route-refresh:api";
    prefix "rr-api";

    import ze-extensions { prefix ze; }

    organization "Ze Project";
    description "Route refresh command RPCs (RFC 2918, RFC 7313).";
    revision 2026-03-08 {
        description "Initial revision.";
    }

    rpc peer-refresh {
        description "Give the family as one word, for example ipv4/unicast. An
unknown word fails with 'invalid family'. RFC 2918 Section 4 permits the
message only where the peer sent the Route Refresh capability. The answer
carries the peer selector and the family.";
        ze:help "Send ROUTE-REFRESH to peer for specified family.";
    }
}
