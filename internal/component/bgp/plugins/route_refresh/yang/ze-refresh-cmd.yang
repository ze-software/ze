module ze-refresh-cmd {
    namespace "urn:ze:refresh:cmd";
    prefix refreshcmd;
    import ze-extensions { prefix ze; }
    description "Request peers to re-send routes (RFC 2918, RFC 7313)";
    // ze-peer-cmd.yang declares that container, and it is the keyword the
    // operator types the selector after.
    revision 2026-10-23 { description "clear soft states that its selector names one peer."; }
    revision 2026-08-29 { description "The peer selector of every command here comes from the request peer container."; }
    revision 2026-03-16 { description "Initial revision"; }

    container request {
        config false;

        container peer {
            config false;

            container refresh {
                config false;
                ze:command "ze-bgp:peer-refresh";
                ze:rpc "ze-route-refresh-api:peer-refresh";
                description "Sends a ROUTE-REFRESH message for the specified AFI/SAFI. The
peer will re-advertise its entire Adj-RIB-Out.";
                ze:help "Ask a peer to re-send all routes (RFC 2918).";
            }

            container borr {
                config false;
                ze:command "ze-bgp:peer-borr";
                ze:rpc "ze-bgp-api:peer-borr";
                description "Tells the peer to mark existing routes as stale. After re-sending,
send EORR to purge anything not refreshed.";
                ze:help "Start an Enhanced Route Refresh cycle (RFC 7313).";
            }

            container eorr {
                config false;
                ze:command "ze-bgp:peer-eorr";
                ze:rpc "ze-bgp-api:peer-eorr";
                description "The peer purges any routes not re-advertised since the matching
BORR. Only send this after the peer has finished re-advertising.";
                ze:help "Finish an Enhanced Route Refresh cycle (RFC 7313).";
            }

            container clear {
                config false;
                description "The session stays established, so no route is withdrawn while it runs. RFC 2918
                             Section 4 permits the request only toward a peer that advertised the Route Refresh
                             Capability.";
                ze:help "Non-disruptive peer refresh.";

                container soft {
                    config false;
                    ze:command "ze-bgp:peer-clear-soft";
                    ze:rpc "ze-bgp-api:peer-clear-soft";
                    description "Sends ROUTE-REFRESH for every negotiated AFI/SAFI, causing the peer
to re-send all routes. No session bounce, no traffic impact. The selector names
one peer: *, an exclusion and a selector matching several peers are refused.
refresh, borr and eorr act on every peer the selector matches.";
                    ze:help "Soft-clear a peer without dropping the session.";
                }
            }
        }
    }
}
