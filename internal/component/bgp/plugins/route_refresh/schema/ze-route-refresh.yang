module ze-route-refresh {
    namespace "urn:ze:route-refresh";
    prefix rr;

    import ze-bgp-conf { prefix bgp; }

    description
        "Route Refresh capability plugin for ZeBGP (RFC 2918, code 2)
         and Enhanced Route Refresh (RFC 7313, code 70).";

    revision 2026-02-22 {
        description "Initial revision.";
    }

    // NOTE: route-refresh container is defined in peer-fields grouping (ze-bgp-conf.yang).
    // These augments are no-ops since the container already exists via uses peer-fields,
    // but they're kept for documentation and forward compatibility.
}
