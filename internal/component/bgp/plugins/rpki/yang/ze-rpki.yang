module ze-rpki {
  namespace "urn:ze:rpki";
  prefix rpki;

  import ze-bgp-conf {
    prefix bgp;
  }

  import ze-types {
    prefix zt;
  }

  import ze-extensions {
    prefix ze;
  }

  // Action applied to a route in a given RPKI validation state.
  // Shared by the global and per-peer/group action blocks so the set of
  // choices stays identical everywhere. Order is display-only.
  typedef validation-action {
    type enumeration {
      enum reject { ze:help "Keep the route in the Adj-RIB-In, marked ineligible, so the decision process never selects it."; }
      enum log-only { ze:help "Keep the route, marked with its state, and write a log line."; }
      enum accept { ze:help "Keep the route and write no log line."; }
    }
    description "RPKI validation-state action (RFC 6811 Section 3: operator-configurable per state)";
  }

  // Per-peer / per-group policy overrides. A subset of rpki-config: only the
  // action blocks, and the leaves carry NO defaults so an unset leaf falls
  // through to the group then the global value (per-leaf inheritance). The
  // transport/enable settings (cache-server, validation-timeout, aspa
  // validation) are global-only and deliberately absent here.
  grouping rpki-peer-policy {
    container rpki {
      description "Ze resolves every leaf on its own. A leaf set on the peer wins. A leaf that
is unset falls through to the group value, then to the global value.";
      ze:help "RPKI action overrides of this peer or group.";

      container action {
        description "A leaf here carries no default, so an unset leaf falls through to the
group value and then to the global value.";
        ze:help "Origin-validation action overrides of this peer or group.";
        leaf invalid {
          type validation-action;
          description "An unset leaf inherits the group value, then the global value.";
          ze:help "Action Ze applies to a route in the Invalid validation state.";
        }
        leaf not-found {
          type validation-action;
          description "An unset leaf inherits the group value, then the global value.";
          ze:help "Action Ze applies to a route in the NotFound validation state.";
        }
      }

      leaf blackhole-exempt {
        type boolean;
        default "false";
        description "The route carries the RFC 7999 BLACKHOLE community, and a covering VRP allows a
shorter prefix than the route announces.

RFC 7999 Section 3.3 states that an operator MUST ensure origin validation does not
inadvertently block legitimate announcements carrying BLACKHOLE. A blackhole prefix is
as long as possible, usually a /32 or a /128. A ROA for the covering block carries its
maxLength at the aggregate. RFC 6811 then makes the announcement Invalid, and a session
running action invalid reject drops the route before anything can honor it.

The exemption is narrow. It applies only when a covering VRP names the route's own
origin AS and disagrees on nothing but the length. A wrong origin AS stays Invalid,
which is the hijack RFC 6811 exists to catch. A prefix with no covering VRP is NotFound
rather than Invalid, so the exemption never reaches it.

The default is false. Enable it together with the blackhole honor leaf of the peer, on
the same session. On its own it accepts a route it would have rejected, and it discards
nothing.";
        ze:help
          "Keep a BLACKHOLE route when its only origin-validation fault is the prefix length.";
      }

      container aspa {
        description "These overrides apply only when ASPA validation is enabled globally.";
        ze:help "ASPA action overrides for this peer or group.";
        container action {
          description "invalid names the action of an ASPA Invalid path and unknown that of an ASPA Unknown path.
Neither leaf carries a default, so an unset leaf falls through to the group value and then to the global value.";
          ze:help "ASPA path-state action overrides of this peer or group.";
          leaf invalid {
            type validation-action;
            description "An unset leaf inherits the group value, then the global value.";
            ze:help "Action Ze applies to a route in the ASPA Invalid path state.";
          }
          leaf unknown {
            type validation-action;
            description "An unset leaf inherits the group value, then the global value.";
            ze:help "Action Ze applies to a route in the ASPA Unknown path state.";
          }
        }
      }
    }
  }

  grouping rpki-config {
    container rpki {
      presence "RPKI origin validation enabled";
      description "The container carries presence. Ze validates a route only when cache-server holds at least one
entry, so an empty container validates nothing. The container also holds the validation timeout, the
origin-validation actions, and the ASPA block. A peer and a group override an action leaf of their own. Neither
can name a cache server, because the RTR transport is global.";
      ze:help "RPKI origin validation of a received route (RFC 6811).";

      list cache-server {
        key "address";
        ordered-by user;
        description "The list key is an IP address or a hostname. Ze tries entries in increasing preference order,
publishes only a completed cache response, and replaces the selected cache's records atomically.
An empty list leaves validation off.";
        ze:help "RTR cache servers Ze reads the validated ROA and ASPA records from.";
        leaf address {
          type string;
          description "The address is the list key, so one entry exists for each cache
server.";
          ze:help "IP address or hostname of the RTR cache server.";
        }
        leaf port {
          type zt:port;
          description "The cache transport port. When omitted, unprotected TCP uses 323 and TLS uses 324.";
          ze:help "TCP port of the RTR cache server.";
        }
        leaf preference {
          type uint8;
          default "100";
          description "The lower the value, the more preferred the cache (RFC 8210 Section 10).
Each polling round starts with the most preferred cache, and ze loads its data from
the first cache that completes a synchronization; caches with equal values keep their
configuration order. A cache that fails, or answers No Data Available, hands the round
to the next one in preference order. While a less-preferred cache holds the data, a
more-preferred cache is asked again when its own Retry Interval runs out, and takes
over once it completes a full load.";
          ze:help "Cache selection order: a lower value is preferred.";
        }
        leaf source-address {
          type zt:ip-address;
          description "Set this leaf when the RTR connection MUST leave the box from one
specific local address.";
          ze:help "Source IP address of an outbound RTR connection.";
        }
        leaf trusted-network {
          type boolean;
          default "false";
          description "Explicit operator selection of unprotected RTR over TCP. Use only when the router and cache
are on the same trusted, controlled network (RFC 8210 Section 9). This setting does not prove network trust
and never permits a TLS-configured cache to fall back to plaintext.";
          ze:help "Permit unprotected RTR only on an explicitly trusted network.";
        }
        container tls {
          presence "Use mutually authenticated TLS for this cache.";
          description "Native RTR over mutual TLS (RFC 8210 Section 9.2). The router presents the named PKI
certificate and its intermediate chain. The cache must request client authentication and present a trusted
DNS-ID certificate; CN-ID is never used. Authentication failure never falls back to unprotected TCP.";
          ze:help "Authenticate the RTR cache and router with TLS.";
          leaf ca-certificate {
              ze:reference "pki-ca";
            type string {
              length "1..255";
              pattern '[A-Za-z0-9._-]+';
            }
            mandatory true;
            description "Named PKI CA used to authenticate this cache. System roots are not used.";
            ze:help "PKI CA certificate trusted for the cache.";
          }
          leaf certificate {
              ze:reference "pki-certificate";
            type string {
              length "1..255";
              pattern '[A-Za-z0-9._-]+';
            }
            mandatory true;
            description "Named PKI router certificate with its private key and a subjectAltName iPAddress identity
matching the connection's source IP address. The certificate must permit TLS client authentication.";
            ze:help "PKI certificate and private key identifying this router.";
          }
          leaf server-name {
            type string {
              length "1..254";
            }
            description "Cache DNS reference identifier, matched against certificate dNSName identities.
Defaults to the cache address when that address is a DNS name. Required for IP-address endpoints.
An IP address, wildcard reference, or certificate common name cannot supply this identity.";
            ze:help "Expected DNS name of the TLS cache.";
          }
        }

      }

      leaf validation-timeout {
        type uint16 {
          range "1..65535";
        }
        default "30";
        units "seconds";
        description "The default is 30 seconds. A longer timeout holds a route in the pending
state for longer. Reloading this leaf refreshes retained routes under the new timeout.";
        ze:help "Fail-open timeout of a route whose validation is pending.";
      }

      container action {
        description "RFC 6811 Section 3 makes the action of each validation state
configurable by the operator.";
        ze:help "Global origin-validation actions.";
        leaf invalid {
          type validation-action;
          default "reject";
          description "The default is reject. The received route remains in Adj-RIB-In but is
ineligible for the decision process until validation or configured policy admits it.";
          ze:help "Action Ze applies to a route in the Invalid validation state.";
        }
        leaf not-found {
          type validation-action;
          default "accept";
          description "The default is accept, which keeps the route and writes no log line.";
          ze:help "Action Ze applies to a route in the NotFound validation state.";
        }
      }

      container aspa {
        description "validation turns the verification on and its default is false. Ze reads an ASPA record over
version 2 of the RTR protocol alone. A session Ze downgrades to version 1 carries none. Ze refuses an ASPA PDU
on a version 1 session as a protocol violation. action holds the action of each path state, and a peer or a
group overrides those two leaves.";
        ze:help "AS_PATH verification against the ASPA records, and the action of each result.";
        leaf validation {
          type boolean;
          default "false";
          description "Ze reads the ASPA records over version 2 of the RTR protocol.";
          ze:help "Verify the AS path of a route against the ASPA records.";
        }
        container action {
          description "invalid holds the action of an ASPA Invalid path and unknown that of an ASPA Unknown path. Both
apply only while aspa validation is true. A peer or a group overrides each leaf.";
          ze:help "Global action Ze applies for each ASPA path state.";
          leaf invalid {
            type validation-action;
            default "reject";
            description "The default is reject. Ze retains the route in the Adj-RIB-In for
re-evaluation and excludes it from route selection until the path becomes acceptable.";
            ze:help "Action Ze applies to a route in the ASPA Invalid path state.";
          }
          leaf unknown {
            type validation-action;
            default "accept";
            description "The default is accept, which keeps the route and writes no log line.";
            ze:help "Action Ze applies to a route in the ASPA Unknown path state.";
          }
        }
      }
    }
  }

  augment "/bgp:bgp" {
    uses rpki-config;
  }

  // Per-peer and per-group action overrides (same three levels the role plugin uses).
  augment "/bgp:bgp/bgp:peer" {
    uses rpki-peer-policy;
  }

  augment "/bgp:bgp/bgp:group/bgp:peer" {
    uses rpki-peer-policy;
  }

  augment "/bgp:bgp/bgp:group" {
    uses rpki-peer-policy;
  }
}
