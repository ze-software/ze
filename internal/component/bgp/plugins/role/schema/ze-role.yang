module ze-role {
    namespace "urn:ze:role";
    prefix role;

    import ze-bgp-conf { prefix bgp; }

    description "RFC 9234 BGP Role plugin for ZeBGP";

    revision 2026-01-01 {
        description "Initial revision";
    }

    typedef role-type {
        type enumeration {
            enum provider { value 0; description "RFC 9234: Provider (0)"; }
            enum rs { value 1; description "RFC 9234: Route Server (1)"; }
            enum rs-client { value 2; description "RFC 9234: RS-Client (2)"; }
            enum customer { value 3; description "RFC 9234: Customer (3)"; }
            enum peer { value 4; description "RFC 9234: Peer (4)"; }
        }
        description "RFC 9234 BGP Role values";
    }

    typedef export-token {
        type union {
            type enumeration {
                enum default { description "RFC 9234 Section 5 default egress rules for the declared role"; }
                enum unknown { description "Also send to peers with no role configured"; }
            }
            type role-type;
        }
        description "Export filter token: default expands to RFC rules, unknown sends to untagged peers, or explicit role name";
    }

    grouping role-config {
        container role {
            description "RFC 9234 BGP Role configuration";

            leaf import {
                type role-type;
                description "Declares local role and enables RFC 9234 ingress rules (replaces Phase 1 name keyword)";
            }

            leaf-list export {
                type export-token;
                description "Controls which destination peer roles may receive routes from this peer";
            }

            leaf strict {
                type boolean;
                default false;
                description "Require peer to send Role capability";
            }
        }
    }

    // Standalone peer
    augment "/bgp:bgp/bgp:peer" {
        uses role-config;
    }

    // Peer inside group
    augment "/bgp:bgp/bgp:group/bgp:peer" {
        uses role-config;
    }

    // Group-level
    augment "/bgp:bgp/bgp:group" {
        uses role-config;
    }
}
