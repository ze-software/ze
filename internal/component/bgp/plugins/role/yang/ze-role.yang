module ze-role {
    namespace "urn:ze:role";
    prefix role;

    import ze-bgp-conf { prefix bgp; }
    import ze-extensions { prefix ze; }

    description "RFC 9234 BGP Role plugin for ZeBGP";

    revision 2026-01-01 {
        description "Initial revision";
    }

    typedef role-type {
        type enumeration {
            enum provider { value 0; ze:help "RFC 9234: Provider (0)"; }
            enum rs { value 1; ze:help "RFC 9234: Route Server (1)"; }
            enum rs-client { value 2; ze:help "RFC 9234: RS-Client (2)"; }
            enum customer { value 3; ze:help "RFC 9234: Customer (3)"; }
            enum peer { value 4; ze:help "RFC 9234: Peer (4)"; }
        }
        description "RFC 9234 BGP Role values";
    }

    typedef export-token {
        type union {
            type enumeration {
                enum default { ze:help "RFC 9234 Section 5 default egress rules for the declared role"; }
                enum unknown { ze:help "Also send to peers with no role configured"; }
            }
            type role-type;
        }
        description "Export filter token: default expands to RFC rules, unknown sends to untagged peers, or explicit role name";
    }

    grouping role-config {
        container role {
            description "The container turns on the role rules for this peer. A peer with no role container sends no
                Role capability, and Ze accepts whatever role the peer declares.";
            ze:help "RFC 9234 BGP Role configuration";

            leaf import {
                type role-type;
                description "Ze sends the role in the Role capability, code 9, and it is the only leaf that makes Ze
                    send it. RFC 9234 Section 4.2 Table 2 permits provider with customer, rs with rs-client, and
                    peer with peer. Ze rejects any other pair with a NOTIFICATION of code 2 and subcode 11.";
                ze:help "Declares local role and enables RFC 9234 ingress rules (replaces Phase 1 name keyword)";
            }

            leaf-list export {
                type export-token;
                description "An empty list filters nothing, and the ingress and egress rules of RFC 9234 Section 5 still
                    run. default expands to the set RFC 9234 Section 5 gives the local role. provider sends to
                    customer and rs-client. customer sends to provider, rs and peer. rs sends to rs-client,
                    rs-client sends to rs and provider, and peer sends to customer and rs-client. unknown matches a
                    peer that sent no Role capability, and a peer whose OPEN Ze never recorded.";
                ze:help "Controls which destination peer roles may receive routes from this peer";
            }

            leaf strict {
                type boolean;
                default false;
                description "The default false accepts a peer that sends no Role capability, which RFC 9234 Section 4.2
                    asks for. true rejects that session with a NOTIFICATION of code 2 and subcode 11. The leaf needs
                    import beside it, because Ze validates no OPEN for a peer that declares no local role.";
                ze:help "Require peer to send Role capability";
            }

            leaf transit-asns {
                type string {
                    length "1..255";
                }
                ze:reference "policy-asn-set";
                description "Names a policy asn-set holding the ASNs of transit providers this router does not
                    peer with, for example a provider reached through another router of the network. It is
                    optional: the provider set is derived from the config, as the remote ASN of every peer whose
                    role import is customer (RFC 9234 Section 3.1: the remote AS is then Ze's provider), and the
                    upstream check uses the union of that derived set and every asn-set a transit-asns leaf
                    names, on any peer or group. RFC 7454 Section 9: the check rejects a route whose AS path
                    carries one of those ASNs, on import from a customer, a peer or an RS-client, and on export
                    to a peer or a route server; the session to a provider never compares its own ASN.";
                ze:help "asn-set of transit providers this router does not peer with";
            }
        }
    }

    // Standalone peer
    augment "/bgp:bgp/bgp:peer" {
        uses role-config;
    }

    // Peer inside group
    augment "/bgp:bgp/bgp:group/bgp:peer" {
        uses role-config;
    }

    // Group-level
    augment "/bgp:bgp/bgp:group" {
        uses role-config;
    }
}
