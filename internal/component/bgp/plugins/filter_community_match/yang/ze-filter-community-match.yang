module ze-filter-community-match {
    namespace "urn:ze:filter-community-match";
    prefix cm;

    import ze-policy-conf { prefix policy; }
    import ze-extensions { prefix ze; }

    description "Community match filter type for the BGP policy framework.
                 Named community-lists with ordered match entries (first match wins)
                 and accept/reject actions. Checks for presence of a community value
                 in the route's standard, large, or extended community attributes.
                 Referenced from peer filter chains as community-match:NAME.
                 Separate from the tag/strip community plugin (bgp-filter-community)
                 because intent differs: filtering vs modification.";

    revision 2026-04-12 {
        description "Initial revision";
    }

    augment "/policy:policy/policy:match" {
        description "The community condition of a match instance: the community match filter
                     registers it, so a build without BGP has no such condition.";
        leaf community {
            type string { length "1..max"; }
            ze:reference "policy-community-match";
            description "The route passes this condition when the named community-match list accepts
                         it: the list's first entry whose community the route carries decides, and a
                         route no entry matches fails. The list is a policy community-match instance:
                         the editor completes the configured ones, and a commit naming any other is
                         refused. A BGP chain judges it; a Loc-RIB chain refuses it, as its routes
                         carry no community.";
            ze:help "Match routes the named community-match list accepts";
        }
    }

    augment "/policy:policy" {
        list community-match {
            ze:filter;
            key "name";
            description "Each list holds an ordered set of match entries. Ze reads
                         the entries in order, and the first match wins. No match is
                         an implicit deny, so the route is rejected.";
            ze:help "Named community match filter instance.";

            leaf name {
                type string;
                description "The filter answers accept or reject for the whole UPDATE, and never rewrites it. A chain
                    that names a list Ze does not hold rejects every route of that peer, because the filter fails
                    closed.";
                ze:help "Filter instance name (referenced in peer filter chains
                         as community-match:NAME).";
            }

            list entry {
                key "community";
                ordered-by user;
                description "Ze reads the entries in order, and the first match wins.
                             An entry checks whether the named community value is
                             present in the route's community attributes.";
                ze:help "Ordered match entry, checked against the route's community attributes.";

                leaf community {
                    type string;
                    description "Standard: ASN:VAL, for example 65001:100, or a
                                 well-known name (no-export, no-advertise,
                                 no-export-subconfed, nopeer, blackhole).
                                 Large: GA:LD1:LD2, for example 65001:100:200.
                                 Extended: a hex string, for example
                                 000200010000000a, or target:ASN:NN, or
                                 origin:ASN:NN. Values are validated at configure
                                 time and matched by their canonical attribute
                                 value, so named and hex extended communities
                                 identify the same eight-octet value.";
                    ze:help "Community value to match.";
                }

                leaf type {
                    type enumeration {
                        enum standard {
                            ze:help "Match in standard community attribute (type 8)";
                        }
                        enum large {
                            ze:help "Match in large community attribute (type 32)";
                        }
                        enum extended {
                            ze:help "Match in extended community attribute (type 16)";
                        }
                    }
                    default standard;
                    description "Ze reads the one attribute the leaf names. An entry of type standard therefore does
                        not see a value that sits in the LARGE COMMUNITIES attribute. Write one entry for each
                        attribute the route can carry the value in.";
                    ze:help "Which community attribute type to check.";
                }

                leaf action {
                    type enumeration {
                        enum accept {
                            ze:help "Accept routes containing this community";
                        }
                        enum reject {
                            ze:help "Reject routes containing this community";
                        }
                    }
                    default accept;
                    description "The first entry whose community the route carries decides the UPDATE, and no later
                        entry is read. A route that carries none of the listed communities is rejected, so a list
                        needs no closing reject entry.";
                    ze:help "Action applied when this community is found in the route.";
                }
            }
        }
    }
}
