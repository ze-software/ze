module ze-hostname {
    namespace "urn:ze:hostname";
    prefix hostname;

    import ze-bgp-conf { prefix bgp; }
    import ze-extensions { prefix ze; }

    description
        "FQDN capability plugin for ZeBGP (draft-walton-bgp-hostname, code 73).
         Advertises hostname and domain name of the BGP speaker.";

    revision 2025-01-29 {
        description "Initial revision.";
    }

    // Standalone peers: augment capability container
    augment "/bgp:bgp/bgp:peer/bgp:session/bgp:capability" {
        container hostname {
            description "Ze sends the FQDN capability, code 73 of draft-walton-bgp-hostname, in the OPEN message. Ze
                sends no capability when host and domain are both empty. A container on the peer replaces the
                container on the group rather than adding to it.";
            ze:help "FQDN capability configuration.";

            leaf host {
                type string {
                    length "0..255";
                }
                description "Ze writes the value with a 1-byte length in front of it, which is why 255 bytes is the
                    limit. Ze does not read the hostname of the box, so an empty leaf sends an empty string.";
                ze:help "System hostname (max 255 bytes).";
            }

            leaf domain {
                type string {
                    length "0..255";
                }
                description "The capability carries host and domain as two separate strings, and Ze joins neither. Ze
                    writes the domain after the host, with its own 1-byte length, which is why 255 bytes is the
                    limit.";
                ze:help "Domain name (max 255 bytes).";
            }
        }
    }

    // Group-level capability
    augment "/bgp:bgp/bgp:group/bgp:session/bgp:capability" {
        container hostname {
            description "Ze sends the FQDN capability, code 73 of draft-walton-bgp-hostname, in the OPEN message. Ze
                sends no capability when host and domain are both empty. A container on the peer replaces the
                container on the group rather than adding to it.";
            ze:help "FQDN capability configuration.";

            leaf host {
                type string {
                    length "0..255";
                }
                description "Ze writes the value with a 1-byte length in front of it, which is why 255 bytes is the
                    limit. Ze does not read the hostname of the box, so an empty leaf sends an empty string.";
                ze:help "System hostname (max 255 bytes).";
            }

            leaf domain {
                type string {
                    length "0..255";
                }
                description "The capability carries host and domain as two separate strings, and Ze joins neither. Ze
                    writes the domain after the host, with its own 1-byte length, which is why 255 bytes is the
                    limit.";
                ze:help "Domain name (max 255 bytes).";
            }
        }
    }

    // Grouped peers: augment capability container
    augment "/bgp:bgp/bgp:group/bgp:peer/bgp:session/bgp:capability" {
        container hostname {
            description "Ze sends the FQDN capability, code 73 of draft-walton-bgp-hostname, in the OPEN message. Ze
                sends no capability when host and domain are both empty. A container on the peer replaces the
                container on the group rather than adding to it.";
            ze:help "FQDN capability configuration.";

            leaf host {
                type string {
                    length "0..255";
                }
                description "Ze writes the value with a 1-byte length in front of it, which is why 255 bytes is the
                    limit. Ze does not read the hostname of the box, so an empty leaf sends an empty string.";
                ze:help "System hostname (max 255 bytes).";
            }

            leaf domain {
                type string {
                    length "0..255";
                }
                description "The capability carries host and domain as two separate strings, and Ze joins neither. Ze
                    writes the domain after the host, with its own 1-byte length, which is why 255 bytes is the
                    limit.";
                ze:help "Domain name (max 255 bytes).";
            }
        }
    }

    // Standalone peers: legacy syntax (in session container)
    augment "/bgp:bgp/bgp:peer/bgp:session" {
        leaf host-name {
            type string {
                length "0..255";
            }
            description "Ze reads the leaf after capability > hostname > host and replaces that value with it, so a
                peer that writes both leaves sends this one. The capability writes a 1-byte length in front of the
                host name, which is the 255-byte limit. Write capability > hostname > host in a new config:
                ze exabgp migrate produces that spelling and never this one.";
            ze:help "Legacy: Host name for FQDN capability.";
        }

        leaf domain-name {
            type string {
                length "0..255";
            }
            description "Ze reads the leaf after capability > hostname > domain and replaces that value with it, so a
                peer that writes both leaves sends this one. The capability writes a 1-byte length in front of the
                domain name, which is the 255-byte limit. Write capability > hostname > domain in a new config:
                ze exabgp migrate produces that spelling and never this one.";
            ze:help "Legacy: Domain name for FQDN capability.";
        }
    }

    // Grouped peers: legacy syntax (in session container)
    augment "/bgp:bgp/bgp:group/bgp:peer/bgp:session" {
        leaf host-name {
            type string {
                length "0..255";
            }
            description "Ze reads the leaf after capability > hostname > host and replaces that value with it, so a
                peer that writes both leaves sends this one. The capability writes a 1-byte length in front of the
                host name, which is the 255-byte limit. Write capability > hostname > host in a new config:
                ze exabgp migrate produces that spelling and never this one.";
            ze:help "Legacy: Host name for FQDN capability.";
        }

        leaf domain-name {
            type string {
                length "0..255";
            }
            description "Ze reads the leaf after capability > hostname > domain and replaces that value with it, so a
                peer that writes both leaves sends this one. The capability writes a 1-byte length in front of the
                domain name, which is the 255-byte limit. Write capability > hostname > domain in a new config:
                ze exabgp migrate produces that spelling and never this one.";
            ze:help "Legacy: Domain name for FQDN capability.";
        }
    }

    // Group-level: legacy syntax (in session container)
    augment "/bgp:bgp/bgp:group/bgp:session" {
        leaf host-name {
            type string {
                length "0..255";
            }
            description "A member peer that states no host-name of its own takes this value. Ze reads the leaf after
                capability > hostname > host and replaces that value with it. The capability writes a 1-byte length
                in front of the host name, which is the 255-byte limit. Write capability > hostname > host in a new
                config: ze exabgp migrate produces that spelling and never this one.";
            ze:help "Legacy: Host name for FQDN capability (group default).";
        }

        leaf domain-name {
            type string {
                length "0..255";
            }
            description "A member peer that states no domain-name of its own takes this value. Ze reads the leaf after
                capability > hostname > domain and replaces that value with it. The capability writes a 1-byte length
                in front of the domain name, which is the 255-byte limit. Write capability > hostname > domain in a new
                config: ze exabgp migrate produces that spelling and never this one.";
            ze:help "Legacy: Domain name for FQDN capability (group default).";
        }
    }
}
