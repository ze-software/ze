module ze-hostname {
    namespace "urn:ze:hostname";
    prefix hostname;

    import ze-bgp-conf { prefix bgp; }

    description
        "FQDN capability plugin for ZeBGP (draft-walton-bgp-hostname, code 73).
         Advertises hostname and domain name of the BGP speaker.";

    revision 2025-01-29 {
        description "Initial revision.";
    }

    // Standalone peers: augment capability container
    augment "/bgp:bgp/bgp:peer/bgp:capability" {
        container hostname {
            description "FQDN capability configuration.";

            leaf host {
                type string {
                    length "0..255";
                }
                description "System hostname (max 255 bytes).";
            }

            leaf domain {
                type string {
                    length "0..255";
                }
                description "Domain name (max 255 bytes).";
            }
        }
    }

    // Group-level capability
    augment "/bgp:bgp/bgp:group/bgp:capability" {
        container hostname {
            description "FQDN capability configuration.";

            leaf host {
                type string {
                    length "0..255";
                }
                description "System hostname (max 255 bytes).";
            }

            leaf domain {
                type string {
                    length "0..255";
                }
                description "Domain name (max 255 bytes).";
            }
        }
    }

    // Grouped peers: augment capability container
    augment "/bgp:bgp/bgp:group/bgp:peer/bgp:capability" {
        container hostname {
            description "FQDN capability configuration.";

            leaf host {
                type string {
                    length "0..255";
                }
                description "System hostname (max 255 bytes).";
            }

            leaf domain {
                type string {
                    length "0..255";
                }
                description "Domain name (max 255 bytes).";
            }
        }
    }

    // Standalone peers: legacy syntax
    augment "/bgp:bgp/bgp:peer" {
        leaf host-name {
            type string {
                length "0..255";
            }
            description "Legacy: Host name for FQDN capability.";
        }

        leaf domain-name {
            type string {
                length "0..255";
            }
            description "Legacy: Domain name for FQDN capability.";
        }
    }

    // Grouped peers: legacy syntax
    augment "/bgp:bgp/bgp:group/bgp:peer" {
        leaf host-name {
            type string {
                length "0..255";
            }
            description "Legacy: Host name for FQDN capability.";
        }

        leaf domain-name {
            type string {
                length "0..255";
            }
            description "Legacy: Domain name for FQDN capability.";
        }
    }

    // Group-level: legacy syntax
    augment "/bgp:bgp/bgp:group" {
        leaf host-name {
            type string {
                length "0..255";
            }
            description "Legacy: Host name for FQDN capability (group default).";
        }

        leaf domain-name {
            type string {
                length "0..255";
            }
            description "Legacy: Domain name for FQDN capability (group default).";
        }
    }
}
