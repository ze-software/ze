module ze-bmp-cmd {
    namespace "urn:ze:bmp:cmd";
    prefix bmpcmd;
    import ze-extensions { prefix ze; }
    // Removing the BMP surface removes these command nodes together with the
    // handlers and the config schema. See ai/rules/plugin-self-containment.md.
    description "The show bmp command tree, owned by the bgp-bmp plugin.";
    revision 2026-06-03 { description "Relocated show bmp ... out of the central show schema (plugin self-containment)."; }

    container show {
        config false;
        ze:help "Read-only commands to inspect system, protocol, and network state.";

        container bmp {
            config false;
            description "BMP is an outbound feed to a collector, so a session here is Ze reporting to a
                         station and never a routing peer.";
            ze:help "BMP monitoring sessions, peers, and routes.";

            container sessions {
                config false;
                ze:command "ze-bgp:show-bmp-sessions";
                description "Lists each session with connection state and message counters.
Check here to confirm your BMP collector is receiving data.";
                ze:help "Show active BMP receiver sessions.";
            }

            container peers {
                config false;
                ze:command "ze-bgp:show-bmp-peers";
                description "Lists peers reported via BMP with their state and route statistics.";
                ze:help "Show BGP peers as seen through BMP monitoring.";
            }

            container collectors {
                config false;
                ze:command "ze-bgp:show-bmp-collectors";
                description "Lists configured collectors with connection state, sent message
counts, and error statistics. Check here if your collector is
not receiving data.";
                ze:help "Show BMP collector connection status.";
            }

            container rib {
                config false;
                ze:command "ze-bgp:show-bmp-rib";
                description "Returns the BMP RIB content. Use this to verify what your
collector is seeing from remote peers.";
                ze:help "Show routes received via BMP monitoring sessions.";
            }
        }
    }
}
