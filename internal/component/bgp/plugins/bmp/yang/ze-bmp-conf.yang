module ze-bmp-conf {
    namespace "urn:ze:bmp:conf";
    prefix bmp;

    import ze-bgp-conf { prefix bgp; }
    import ze-types { prefix zt; }
    import ze-extensions { prefix ze; }

    description "BMP (BGP Monitoring Protocol, RFC 7854) configuration for Ze.
                 Receiver listener lives under environment (like web, ssh, lg).
                 Sender and protocol options live under bgp.";

    revision 2026-04-12 {
        description "Initial revision";
    }

    // --- Receiver: environment { bmp { ... } } ---

    container environment {
        description "The bmp container under it holds the receiver alone. The BMP sender of Ze
                     lives under bgp bmp, so a box that only sends BMP writes nothing here.";
        ze:help "Environment settings for BMP receiver";

        container bmp {
            description "The receiver starts only when enabled is true and the server list holds
                         one entry at least. Ze stores each Route Monitoring message it accepts
                         in the BMP RIB, and show bmp rib reads that RIB.";
            ze:help "BMP receiver settings";

            leaf enabled {
                type boolean;
                default false;
                description "The default is false. The receiver needs this leaf true and one
                             server entry at least, so enabled true on its own binds no address.";
                ze:help "Enable BMP receiver";
            }

            list server {
                key "name";
                ze:listener;
                description "The ze:listener extension marks this list, so config validation
                             refuses a second listener that binds the same protocol, port and
                             address. Ze opens one TCP listener for each entry. A bind that
                             fails is logged, and the other entries keep their listener. An
                             empty list binds nothing, because the receiver has no default
                             endpoint.";
                ze:help "BMP receiver listen endpoints";

                leaf name {
                    type string;
                    description "The name is the list key alone. Ze binds the ip and the port of
                                 each entry and reads no name, so the name only keeps two
                                 entries of the list apart.";
                    ze:help "Listener instance name";
                }

                uses zt:listener {
                    refine ip {
                        default "0.0.0.0";
                    }
                    refine port {
                        default 11019;
                    }
                }
            }

            leaf max-sessions {
                type uint16 {
                    range "1..1000";
                }
                default 100;
                description "The default is 100 and the range is 1 to 1000. The count is per
                             listener, so two server entries admit twice this number of
                             sessions. Over the limit Ze closes the new connection and logs a
                             warning, and the sessions already open keep running.";
                ze:help "Maximum concurrent BMP sessions";
            }

            leaf route-action {
                type enumeration {
                    enum monitor {
                        ze:help "Store in BMP RIB for visibility (show bmp rib), isolated from BGP best-path and FIB";
                    }
                }
                default monitor;
                description "monitor is the default and the only value. The routes of a BMP Route
                    Monitoring message go to the BMP RIB, which show bmp rib reads. They reach neither
                    BGP best-path selection nor the FIB, because a BMP receiver is a monitoring station:
                    RFC 7854 defines no use of the routes it is told about. Any other value is refused
                    when the config loads. The leaf stays with one value on purpose: a value removed
                    from the enumeration is refused, while a removed leaf would be skipped in silence.";
                ze:help "Action for received BMP Route Monitoring messages";
            }
        }
    }

    // --- Sender + protocol options: bgp { bmp { ... } } ---

    grouping bmp-bgp-config {
        container bmp {
            description "The container holds the sender. The BMP receiver of Ze listens under environment bmp, so a box
                that only receives BMP writes nothing here.";
            ze:help "BMP sender and protocol options";

            container sender {
                presence "BMP sender enabled";
                description "The container carries presence, so Ze starts the sender when you write it and stops every
                    collector session when you delete it. Ze sends an Initiation message first on each connection,
                    which RFC 7854 Section 4.3 requires.";
                ze:help "Stream BMP data to external collectors";

                list collector {
                    key "name";
                    description "Ze dials each collector from its own session. Ze retries a failed connection after 30
                        seconds, then doubles the wait to a limit of 720 seconds. A collector whose address, port
                        and source-address a reload does not change keeps its session, and keeps everything the
                        collector learned on it.";
                    ze:help "BMP collector endpoints to connect to";

                    leaf name {
                        type string;
                        description "The name is the list key and names the collector in every bmp log line. Ze does not
                            send the name to the collector. A rename ends the session with a Termination message and
                            opens a new one.";
                        ze:help "Collector instance name";
                    }

                    leaf address {
                        type zt:ip-address;
                        mandatory true;
                        description "The leaf is mandatory, because a collector with no address has nothing to dial.
                            The address is part of the session identity. A reload that changes it ends the session
                            with a Termination message, then opens a new one.";
                        ze:help "Collector IP address";
                    }

                    leaf port {
                        type zt:port;
                        default 11019;
                        description "11019 is also the default port of the BMP receiver of Ze, under environment bmp
                            server. Two Ze boxes therefore connect with no port written on either side. The port is
                            part of the session identity, so a reload that changes it opens a new session.";
                        ze:help "Collector TCP port";
                    }

                    leaf source-address {
                        type zt:ip-address;
                        description "Ze binds the address on the outbound connection. When the leaf is absent, the kernel
                            picks the source address of the route to the collector. The address is part of the
                            session identity, so a reload that changes it opens a new session.";
                        ze:help "Source IP address for outbound BMP connections";
                    }
                }

                leaf route-monitoring-policy {
                    type enumeration {
                        enum pre-policy { ze:help "Stream the UPDATE messages Ze received, the Adj-RIB-In."; }
                        enum post-policy { ze:help "Stream the UPDATE messages Ze sent, the Adj-RIB-Out (RFC 8671)."; }
                        enum all { ze:help "Stream both the received and the sent UPDATE messages."; }
                    }
                    default "all";
                    description "pre-policy streams the UPDATE messages Ze received, post-policy streams the UPDATE
                        messages Ze sent, and all streams both. A change to the leaf bounces every monitored peer
                        with a Peer Down and a Peer Up, which RFC 8671 Section 7.2 requires. The BMP session itself
                        stays up.";
                    ze:help "Which routes to stream: pre-policy (Adj-RIB-In), post-policy (Adj-RIB-Out, RFC 8671), or all";
                }

                leaf route-mirroring {
                    type boolean;
                    default false;
                    description "Ze mirrors every OPEN, UPDATE, NOTIFICATION, KEEPALIVE and ROUTE-REFRESH message it
                        processes, in a TLV of type 0. The stream carries every message of every peer, so the
                        default is false. A change to the leaf bounces every monitored peer with a Peer Down and a
                        Peer Up, which RFC 8671 Section 7.2 requires.";
                    ze:help "Enable Route Mirroring (RFC 7854 S4.7): stream verbatim copies of all BGP messages to collectors";
                }

                leaf loc-rib {
                    type boolean;
                    default false;
                    description "Ze streams each best-path change of the local RIB to the collectors as a Route Monitoring message.
                        The message carries a Loc-RIB peer header, which RFC 9069 gives PeerType 3.";
                    ze:help "Enable Loc-RIB monitoring (RFC 9069).";
                }

                leaf statistics-timeout {
                    type uint16 {
                        range "0..65535";
                    }
                    default 0;
                    units "seconds";
                    description "The unit is seconds and the range is 0 to 65535. The default is 0, and Ze sends no
                        Statistics Report (RFC 7854 Section 4.8) at any value. The periodic timer this leaf
                        configures is not implemented, so the leaf changes what the sender configuration carries and
                        nothing on the wire. A change to the leaf still bounces every session of the sender with a
                        Peer Down and Peer Up sequence. Ze does this because it compares the whole declared
                        sender behavior.";
                    ze:help "Interval for periodic statistics reports (0 = disabled)";
                }
            }
        }
    }

    augment "/bgp:bgp" {
        uses bmp-bgp-config;
    }
}
