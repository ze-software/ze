module ze-bmp-conf {
    namespace "urn:ze:bmp:conf";
    prefix bmp;

    import ze-bgp-conf { prefix bgp; }
    import ze-types { prefix zt; }
    import ze-extensions { prefix ze; }

    description "BMP (BGP Monitoring Protocol, RFC 7854) configuration for Ze.
                 Receiver listener lives under environment (like web, ssh, lg).
                 Sender and protocol options live under bgp.";

    revision 2026-04-12 {
        description "Initial revision";
    }

    // --- Receiver: environment { bmp { ... } } ---

    container environment {
        description "Environment settings for BMP receiver";

        container bmp {
            description "BMP receiver settings";

            leaf enabled {
                type boolean;
                default false;
                description "Enable BMP receiver";
            }

            list server {
                key "name";
                ze:listener;
                description "BMP receiver listen endpoints";

                leaf name {
                    type string;
                    description "Listener instance name";
                }

                uses zt:listener {
                    refine ip {
                        default "0.0.0.0";
                    }
                    refine port {
                        default 11019;
                    }
                }
            }

            leaf max-sessions {
                type uint16 {
                    range "1..1000";
                }
                default 100;
                description "Maximum concurrent BMP sessions";
            }
        }
    }

    // --- Sender + protocol options: bgp { bmp { ... } } ---

    grouping bmp-bgp-config {
        container bmp {
            description "BMP sender and protocol options";

            container sender {
                presence "BMP sender enabled";
                description "Stream BMP data to external collectors";

                list collector {
                    key "name";
                    description "BMP collector endpoints to connect to";

                    leaf name {
                        type string;
                        description "Collector instance name";
                    }

                    leaf address {
                        type zt:ip-address;
                        mandatory true;
                        description "Collector IP address";
                    }

                    leaf port {
                        type zt:port;
                        default 11019;
                        description "Collector TCP port";
                    }
                }

                leaf route-monitoring-policy {
                    type enumeration {
                        enum pre-policy;
                        enum post-policy;
                        enum all;
                    }
                    default "all";
                    description "Which routes to stream: pre-policy (Adj-RIB-In), post-policy (Adj-RIB-Out, RFC 8671), or all";
                }

                leaf route-mirroring {
                    type boolean;
                    default false;
                    description "Enable Route Mirroring (RFC 7854 S4.7): stream verbatim copies of all BGP messages to collectors";
                }

                leaf statistics-timeout {
                    type uint16 {
                        range "0..65535";
                    }
                    default 0;
                    units "seconds";
                    description "Interval for periodic statistics reports (0 = disabled)";
                }
            }
        }
    }

    augment "/bgp:bgp" {
        uses bmp-bgp-config;
    }
}
