module ze-bmp-cmd {
    namespace "urn:ze:bmp:cmd";
    prefix bmpcmd;
    import ze-extensions { prefix ze; }
    description "show bmp ... command tree. Owned by the bgp-bmp plugin so that removing the BMP surface removes these command nodes together with the handlers and config schema. See ai/rules/plugin-self-containment.md.";
    revision 2026-06-03 { description "Relocated show bmp ... out of the central show schema (plugin self-containment)."; }

    container show {
        config false;
        description "Read-only commands to inspect system, protocol, and network state";

        container bmp {
            config false;
            description "BMP monitoring sessions, peers, and routes";

            container sessions {
                config false;
                ze:command "ze-show:bmp-sessions";
                description "Show active BMP receiver sessions.
Lists each session with connection state and message counters.
Check here to confirm your BMP collector is receiving data.";
            }

            container peers {
                config false;
                ze:command "ze-show:bmp-peers";
                description "Show BGP peers as seen through BMP monitoring.
Lists peers reported via BMP with their state and route statistics.";
            }

            container collectors {
                config false;
                ze:command "ze-show:bmp-collectors";
                description "Show BMP collector connection status.
Lists configured collectors with connection state, sent message
counts, and error statistics. Check here if your collector is
not receiving data.";
            }

            container rib {
                config false;
                ze:command "ze-show:bmp-rib";
                description "Show routes received via BMP monitoring sessions.
Returns the BMP RIB content. Use this to verify what your
collector is seeing from remote peers.";
            }
        }
    }
}
