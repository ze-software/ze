module ze-update-cmd {
    namespace "urn:ze:update:cmd";
    prefix updatecmd;
    import ze-extensions { prefix ze; }
    description "Send BGP UPDATE messages to peers";
    revision 2026-03-16 { description "Initial revision"; }

    container peer {
        config false;
        description "Per-peer UPDATE operations";

        container update {
            config false;
            ze:command "ze-bgp:peer-update";
            description "Send a pre-built BGP UPDATE to a peer.
Payload can be text (human-readable route syntax), hex, or base64.
Use 'show bgp encode' to build the payload, then send it here.";
        }
    }
}
