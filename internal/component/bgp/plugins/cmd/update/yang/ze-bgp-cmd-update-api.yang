module ze-bgp-cmd-update-api {
  namespace "urn:ze:bgp:cmd:update:api";
  prefix bgp-cmd-update;

  import ze-extensions { prefix ze; }

  description
    "Ze BGP route announcement parsing command RPCs.";

  rpc peer-update {
    description "The first word after update names the encoding, and it is one of text, hex,
b64 and cursor. A BGP reactor must be running, and any other first word is refused as an
unknown encoding.";
    ze:help "Parse and send text-format UPDATE to peer.";
  }
  // The hex and b64 forms are encodings of peer-update above, and handleUpdate
  // reads the encoding from the first word after update. They are not a command
  // of their own, so peer-update-hex published a method no handler answered.
}
