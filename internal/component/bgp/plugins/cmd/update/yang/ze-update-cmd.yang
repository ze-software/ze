module ze-update-cmd {
    namespace "urn:ze:update:cmd";
    prefix updatecmd;
    import ze-extensions { prefix ze; }
    description "Send BGP UPDATE messages to peers";
    revision 2026-03-16 { description "Initial revision"; }
    revision 2026-09-05 { description "The encoding word is a declared enumeration, and the dispatcher refuses a fifth word before the handler runs. Completion offers the four the handler reads. The route expression after that word stays a tail ParseUpdateText owns. It is a recursive attribute and NLRI grammar that no flat leaf list can state, and ze:help names the page that does. The form answers at one path, send bgp, and the peer path it answered at before is gone. The bgp container declares the selector on the keyword the operator types it after."; }

    container send {
        config false;

        container bgp {
            config false;

            // No description on either container. The send and bgp nodes are
            // shared with ze-raw-cmd, and mergeYANGEntry warns when two modules
            // describe one node differently. The text those nodes carry, and the
            // selector leaf every command below bgp inherits, are ze-raw-cmd's.

            container update {
                config false;
                ze:command "ze-bgp:peer-update";
                ze:rpc "ze-bgp-api:peer-update";
                description "The encoding word says how the rest of the line is read. text is the
route syntax docs/architecture/api/update-syntax.md states, hex and b64 are wire octets, and
cursor replays a stored position. 'show bgp encode' builds a hex payload. The tokens after
the encoding word are that encoding's own grammar, and this model states the encoding
alone.";
                ze:help "Send a pre-built BGP UPDATE to a peer.";
                leaf encoding {
                    type enumeration {
                        enum text { ze:help "Read the tokens as the route syntax update-syntax.md states."; }
                        enum hex { ze:help "Read the attributes and the NLRI as hexadecimal wire octets."; }
                        enum b64 { ze:help "Read the attributes and the NLRI as base64 wire octets."; }
                        enum cursor { ze:help "Read the tokens as a delta against this process's stored attributes."; }
                    }
                    mandatory true;
                    description "The word is required and any other word there is refused before the
handler runs. hex and b64 keep the structure of text with the octets in place of the words.
cursor keeps the attributes of the last command per process and peer, so a later command
names only what changed, and 'cursor done' clears them.";
                    ze:help "How the tokens after this word are read.";
                }
            }
        }
    }
}
