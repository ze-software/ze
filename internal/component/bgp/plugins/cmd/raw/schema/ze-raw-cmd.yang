module ze-raw-cmd {
    namespace "urn:ze:raw:cmd";
    prefix rawcmd;
    import ze-extensions { prefix ze; }
    description "Inject raw bytes into a BGP peer session (testing only)";
    revision 2026-03-16 { description "Initial revision"; }

    container peer {
        config false;
        description "Raw byte injection (testing and conformance only)";

        container raw {
            config false;
            ze:command "ze-bgp:peer-raw";
            description "Send raw bytes into a peer's TCP stream (dangerous).
Injects arbitrary bytes with no BGP framing or validation. Intended
for conformance testing and fuzzing only. Will likely break the
session if used carelessly.";
            leaf selector { type string; mandatory true; description "Peer selector"; }
        }
    }
}
