module ze-raw-cmd {
    namespace "urn:ze:raw:cmd";
    prefix rawcmd;
    import ze-extensions { prefix ze; }
    description "Inject raw bytes into a BGP peer session (testing only)";
    revision 2026-10-18 { description "The peer selector summary names * for every peer, so the selector guard's refusal, which quotes it, names the explicit every-peer form."; }
    revision 2026-03-16 { description "Initial revision"; }
    revision 2026-09-05 { description "The raw form states the arguments its handler reads: an encoding enumeration, a data value it always needs, and an optional message type. The dispatcher refuses a word outside either enumeration before the handler runs. The message type takes the type keyword in front of it, because a keyword introduces every value a command runs without. The form answers at one path, send bgp, and the peer path it answered at before is gone. The bgp container declares the selector on the keyword the operator types it after."; }

    container send {
        config false;
        // The top-level send verb root. The protocol keyword comes FIRST, so the
        // one free-form slot stands behind a closed set that says how to read it.
        // Each protocol declares its own destination leaf on its own container:
        // nothing central enumerates the protocols, and nothing reads a
        // destination's kind from the shape of its value.
        description "The protocol keyword picks the wire. The value after it names the
                     destination, and each protocol states the vocabulary for that value.";
        ze:help "Put an operator-supplied message on a wire.";

        container bgp {
            config false;
            // The selector leaf sits HERE, on the protocol container, because
            // inheritArgDefs anchors a container's leaves to that container's
            // keyword. The anchor is what binds the bare token after `bgp`
            // (anchoredDef, internal/component/plugin/server/command.go).
            //
            // This module declares the text every send form below `bgp` shares.
            // ze-update-cmd re-declares the two containers with no description,
            // because mergeYANGEntry warns when two modules describe one node
            // differently.
            description "The selector accepts an address, a configured peer name, an AS pattern,
                         a glob, a comma-separated list, or *. A selector that matches no
                         session sends to nothing, and it does not send to every peer.";
            ze:help "Send a message to the BGP peer sessions a selector picks.";
            leaf selector {
                type string;
                mandatory true;
                description "The value is an IP address, a peer name, an AS pattern such as as65001, a
glob, a comma-separated list of those, or * for every peer. The message goes to each
session the selector matches.";
                ze:help "* for every peer, or an address, a peer name or an AS pattern";
            }

            container raw {
                config false;
                ze:command "ze-bgp:peer-raw";
                ze:rpc "ze-bgp-api:peer-raw";
                description "Injects arbitrary bytes with no BGP framing and no validation. It is for
conformance testing and fuzzing only, and it will break the session if it is used
carelessly. With a type keyword ze writes the marker and the header, and the data carries
the message body alone. Without a type keyword the data carries the whole packet, marker
and header included.";
                ze:help "Send raw bytes into a peer's TCP stream (dangerous).";
                leaf encoding {
                    type enumeration {
                        enum hex { ze:help "Read the data as hexadecimal digits, two per byte."; }
                        enum b64 { ze:help "Read the data as standard base64 with padding."; }
                    }
                    mandatory true;
                    description "The word is required and it is typed before the data. Ze decodes the data
with it, and data the decoder refuses is an error.";
                    ze:help "How the data below is encoded.";
                }
                // No length is stated here, and the absence is a decision. raw exists
                // to put a malformed or oversized frame on one session, and the
                // negotiated maximum message size is the reactor's to enforce
                // (bgp/reactor/session_write.go). A bound stated here would refuse the
                // oversize frame before it reached the check that exists to refuse it.
                leaf data {
                    type string;
                    mandatory true;
                    description "The value is one token, the octets in the encoding named before it. With
a type keyword after it, the octets are the message body alone. Without one, they are the
whole packet, marker and header included.";
                    ze:help "The bytes to send, in the encoding above.";
                }
                leaf type {
                    type enumeration {
                        enum open { ze:help "Write an OPEN header, type 1, in front of the data."; }
                        enum update { ze:help "Write an UPDATE header, type 2, in front of the data."; }
                        enum notification { ze:help "Write a NOTIFICATION header, type 3, in front of the data."; }
                        enum keepalive { ze:help "Write a KEEPALIVE header, type 4, in front of the data."; }
                        enum route-refresh { ze:help "Write a ROUTE-REFRESH header, type 5, in front of the data."; }
                    }
                    description "The word is optional and any other word there is refused. With it, Ze
writes the 16-byte marker and the length and type fields, and the data is the body. Absent,
the data is sent as it is.";
                    ze:help "The BGP message type ze writes a header for.";
                }
            }
        }
    }
}
