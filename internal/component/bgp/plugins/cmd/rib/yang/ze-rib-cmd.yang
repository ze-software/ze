module ze-rib-cmd {
    namespace "urn:ze:rib:cmd";
    prefix ribcmd;
    import ze-extensions { prefix ze; }
    import ze-types { prefix zt; }
    description "BGP RIB operations: query routes, manage Adj-RIB, inject test routes";
    revision 2026-10-17 { description "clear bgp rib in and clear bgp rib out declare their peer selector as a mandatory leaf, so the bare prefix is refused rather than reaching the plugin, and * is the explicit form for every peer. clear bgp rib out declares the optional family it already read from the second token."; }
    revision 2026-09-15 { description "show bgp rib protocol and request bgp rib fastpath are declared here, each stating its own argument. Both were reachable only through the plugin dispatch fallback, and each spelled its grammar in the summary sentence because the model declared no argument. The protocol leaf is a string the bgp-rib plugin checks against the protocol registry, which is the one list of the protocols this binary carries. The fastpath action is a closed set of three words, so it is an enumeration and the dispatcher refuses any other word by name."; }
    revision 2026-03-16 { description "Initial revision"; }

    container show {
        config false;

        container bgp {
            config false;
            description "Typed with no subcommand, lists every peer with state, ASN,
prefixes received, and uptime. Optionally scope by address family: ipv4, ipv6,
or l2vpn.";
            ze:help "BGP peers, sessions, RIB, and protocol tools.";

            container rib {
                config false;
                ze:command "ze-bgp:rib-routes";
                ze:rpc "ze-rib-api:show";
                ze:task-support required;
                description "Look at received or advertised routes with flexible filters: peer,
family, prefix, AS path regex, community, match expression. Pipe
operators: | count, | histogram, | graph. This is the main
route inspection command.";
                ze:help "Query routes in the BGP RIB.";

                container best {
                    config false;
                    ze:command "ze-bgp:rib-best";
                    ze:rpc "ze-rib-api:best";
                    description "Same filters as 'show bgp rib'. Use '| reason' to see why each
path was selected (local-pref, AS path length, MED, etc.).";
                    ze:help "Show the winning route for each prefix.";

                    container status {
                        config false;
                        ze:command "ze-bgp:rib-best-status";
                        ze:rpc "ze-rib-api:best-status";
                        description "Reports idle, pending, or running, plus the last run duration.";
                        ze:help "Check whether best-path computation is still running.";
                    }
                }

                container status {
                    config false;
                    ze:command "ze-bgp:rib-status";
                    ze:rpc "ze-rib-api:status";
                    description "Shows total peers, received/accepted/advertised route counts, and
per-family breakdowns. Use this to confirm convergence after a
peer comes up.";
                    ze:help "Get a quick RIB overview without dumping routes.";
                }

                container rpf {
                    config false;
                    ze:command "ze-bgp:rib-rpf";
                    description "Performs a longest-prefix-match and returns the best-path entry.
Use this to verify RPF checks would pass for a given source.";
                    ze:help "Reverse-path forwarding lookup in the Loc-RIB.";
                }

                container protocol {
                    config false;
                    ze:command "ze-bgp:rib-protocol";
                    description "Answers the same rows as show bgp rib, limited to the Adj-RIB-In
tables one protocol feeds. bgp reads the BGP peers. Every other protocol, bmp for
example, reads the tables its monitored peers fill. The pipeline words after the
protocol are the ones show bgp rib takes: peer <selector> limits the answer to
the matching peers, then filters, then one terminal.";
                    ze:help "Query the routes one protocol feeds into the RIB.";

                    leaf protocol {
                        type string { length "1..32"; }
                        mandatory true;
                        description "The name of a registered protocol. The bgp-rib plugin refuses a
name the protocol registry does not hold and names the registered ones.";
                        ze:help "Registered protocol name";
                    }
                }
            }
        }
    }

    container clear {
        config false;

        container bgp {
            config false;
            description "The subcommands reset what the session holds and leave the configuration alone. A
                         cleared peer renegotiates and relearns rather than reloading its config.";
            ze:help "BGP operational state.";

            container rib {
                config false;
                description "The two directions are separate: in re-reads what the peer sent, and out resends
                             what Ze advertised. Neither changes a policy, so a route a filter rejects stays
                             rejected after the clear.";
                ze:help "Clear and re-advertise RIB entries.";

                container in {
                    config false;
                    ze:command "ze-bgp:rib-clear-in";
                    ze:rpc "ze-rib-api:clear-in";
                    ze:task-support forbidden;
                    description "Wipes the Adj-RIB-In for the peers the selector matches. They will
need to re-advertise everything (or you can send a route-refresh). The selector is
mandatory: clear bgp rib in alone is refused, and * is the explicit form for every peer.";
                    ze:help "Remove all routes received from a peer.";

                    leaf selector {
                        type zt:peer-selector;
                        mandatory true;
                        description "The value is an IP address, a peer name, an AS pattern such as as65001,
a glob, a comma-separated list of those, or * for every peer. The Adj-RIB-In of each
peer it matches is wiped.";
                        ze:help "* for every peer, or an address, a peer name or an AS pattern";
                    }
                }

                container out {
                    config false;
                    ze:command "ze-bgp:rib-clear-out";
                    ze:rpc "ze-rib-api:clear-out";
                    ze:task-support forbidden;
                    description "Triggers a full Adj-RIB-Out replay to the selected peers. Useful
after a policy change to push updated attributes without tearing down the session. The
selector is mandatory: clear bgp rib out alone is refused, and * is the explicit form for
every peer. A family typed after its keyword, as family ipv4/unicast, limits the replay to
that family.";
                    ze:help "Re-advertise all routes to a peer.";

                    leaf selector {
                        type zt:peer-selector;
                        mandatory true;
                        description "The value is an IP address, a peer name, an AS pattern such as as65001,
a glob, a comma-separated list of those, or * for every peer. The Adj-RIB-Out of each
peer it matches is replayed.";
                        ze:help "* for every peer, or an address, a peer name or an AS pattern";
                    }
                    leaf family {
                        type zt:address-family;
                        description "An address family such as ipv4/unicast. Absent, every family the
session negotiated is replayed.";
                        ze:help "Address family to replay, such as ipv4/unicast";
                    }
                }
            }
        }
    }

    container request {
        config false;

        container bgp {
            config false;
            description "These act on the live sessions. Nothing here writes configuration, so a restart
                         returns the daemon to what its config describes.";
            ze:help "BGP operational actions.";

            container rib {
                config false;
                description "The actions inject or withdraw a route directly, without a peer having announced
                             it. A route added this way is not in the configuration and does not survive a
                             restart.";
                ze:help "Request BGP RIB actions.";

                container inject {
                    config false;
                    ze:command "ze-bgp:rib-inject";
                    ze:rpc "ze-rib-api:inject";
                    ze:task-support forbidden;
                    description "Behaves as if the route was received from a peer. Use this for
testing policy filters or simulating route announcements.";
                    ze:help "Inject a synthetic route into the Adj-RIB-In.";
                }

                container withdraw {
                    config false;
                    ze:command "ze-bgp:rib-withdraw";
                    ze:rpc "ze-rib-api:withdraw";
                    ze:task-support forbidden;
                    description "Removes a previously injected or received route from a peer's
Adj-RIB-In, triggering best-path recomputation.";
                    ze:help "Withdraw a route from the Adj-RIB-In.";
                }

                container fastpath {
                    config false;
                    ze:command "ze-bgp:rib-fastpath";
                    ze:task-support forbidden;
                    description "The fast path hands a forward handle to the Loc-RIB consumer
without copying the route. enable and disable switch it, and status reports the
counters. Each of the three answers the same counter snapshot.";
                    ze:help "Switch or report the zero-copy forward-handle fast path.";

                    leaf action {
                        type enumeration {
                            enum enable { description "Start handing forward handles to the consumer."; }
                            enum disable { description "Stop handing forward handles to the consumer."; }
                            enum status { description "Report the counters and change nothing."; }
                        }
                        mandatory true;
                        description "One of the three words. Any other word is refused by name.";
                        ze:help "enable, disable or status";
                    }
                }
            }
        }
    }
}
