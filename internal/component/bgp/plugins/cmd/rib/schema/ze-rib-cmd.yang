module ze-rib-cmd {
    namespace "urn:ze:rib:cmd";
    prefix ribcmd;
    import ze-extensions { prefix ze; }
    description "BGP RIB operations: query routes, manage Adj-RIB, inject test routes";
    revision 2026-03-16 { description "Initial revision"; }

    container show {
        config false;
        description "Read operational state";

        container bgp {
            config false;
            description "BGP peers, sessions, RIB, and protocol tools";

            container rib {
                config false;
                ze:command "ze-rib-api:routes";
                ze:task-support required;
                description "Query routes in the BGP RIB.
Look at received or advertised routes with flexible filters: peer,
family, prefix, AS path regex, community, match expression. Pipe
operators: | count, | prefix-summary, | graph. This is the main
route inspection command.";

                container best {
                    config false;
                    ze:command "ze-rib-api:best";
                    description "Show the winning route for each prefix.
Same filters as 'show bgp rib'. Use '| reason' to see why each
path was selected (local-pref, AS path length, MED, etc.).";

                    container status {
                        config false;
                        ze:command "ze-rib-api:best-status";
                        description "Check whether best-path computation is still running.
Reports idle, pending, or running, plus the last run duration.";
                    }
                }

                container status {
                    config false;
                    ze:command "ze-rib-api:status";
                    description "Get a quick RIB overview without dumping routes.
Shows total peers, received/accepted/advertised route counts, and
per-family breakdowns. Use this to confirm convergence after a
peer comes up.";
                }

                container rpf {
                    config false;
                    ze:command "ze-rib-api:rpf";
                    description "Reverse-path forwarding lookup in the Loc-RIB.
Performs a longest-prefix-match and returns the best-path entry.
Use this to verify RPF checks would pass for a given source.";
                }
            }
        }
    }

    container clear {
        config false;
        description "Reset runtime counters and state without touching configuration";

        container bgp {
            config false;
            description "BGP operational state";

            container rib {
                config false;
                description "Clear and re-advertise RIB entries";

                container in {
                    config false;
                    ze:command "ze-rib-api:clear-in";
                    ze:task-support forbidden;
                    description "Remove all routes received from a peer.
Wipes the Adj-RIB-In for matched peers. They will need to
re-advertise everything (or you can send a route-refresh).
Selector: IP, name, AS pattern, glob, or *.";
                }

                container out {
                    config false;
                    ze:command "ze-rib-api:clear-out";
                    ze:task-support forbidden;
                    description "Re-advertise all routes to a peer.
Triggers a full Adj-RIB-Out replay to the selected peers. Useful
after a policy change to push updated attributes without tearing
down the session. Selector: IP, name, AS pattern, glob, or *.";
                }
            }
        }
    }

    container request {
        config false;
        description "Request an operational action";

        container bgp {
            config false;
            description "BGP operational actions";

            container rib {
                config false;
                description "Request BGP RIB actions";

                container inject {
                    config false;
                    ze:command "ze-rib-api:inject";
                    ze:task-support forbidden;
                    description "Inject a synthetic route into the Adj-RIB-In.
Behaves as if the route was received from a peer. Use this for
testing policy filters or simulating route announcements.";
                }

                container withdraw {
                    config false;
                    ze:command "ze-rib-api:withdraw";
                    ze:task-support forbidden;
                    description "Withdraw a route from the Adj-RIB-In.
Removes a previously injected or received route from a peer's
Adj-RIB-In, triggering best-path recomputation.";
                }
            }
        }
    }
}
