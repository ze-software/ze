module ze-cli-commit-cmd {
    namespace "urn:ze:cli:commit:cmd";
    prefix clicommitcmd;
    import ze-extensions { prefix ze; }
    description "Named commit groups for atomic route updates";
    revision 2026-03-16 { description "Initial revision"; }

    container request {
        config false;

        container commit {
            config false;
            ze:command "ze-bgp:commit";
            ze:rpc "ze-bgp-api:commit";
            description "Actions: start (begin a commit), end (finalize), eor (signal end of
RIB), rollback (undo), show (inspect), withdraw (remove all routes
in a commit), list (show all commits). Grammar: request commit <action>
<name> [args].";
            ze:help "Group route changes into named atomic commits.";
        }
    }
}
