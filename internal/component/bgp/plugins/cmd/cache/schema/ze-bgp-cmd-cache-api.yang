module ze-bgp-cmd-cache-api {
    namespace "urn:ze:bgp:cmd:cache:api";
    prefix "bgp-cache-api";

    organization "Ze Project";
    description "BGP message cache command RPCs.";
    revision 2026-03-08 {
        description "Initial revision.";
    }

    rpc cache {
        description "BGP message cache operations (list, retain, release, expire, forward).";
    }
}
