module ze-cli-cache-cmd {
    namespace "urn:ze:cli:cache:cmd";
    prefix clicachecmd;
    import ze-extensions { prefix ze; }
    description "BGP message cache for deferred forwarding and replay";
    revision 2026-09-05 { description "cache forward answers at send bgp <selector> cached <id>. It puts a whole UPDATE on each matched peer's wire, so it belongs under the verb that sends rather than under request. Its own selector leaf goes: the bgp container declares the one every command below it reads."; }
    revision 2026-03-16 { description "Initial revision"; }
    revision 2026-06-04 { description "Verb-first grammar: show cache (read), request cache (actions)."; }

    container show {
        config false;

        container cache {
            config false;
            ze:command "ze-bgp:cache-list";
            ze:rpc "ze-bgp-api:cache";
            description "The answer carries two keys, 'ids' and 'count'. An ID is listed while its entry
is retained, or while that entry has not expired. The IDs come alone, with no
retain flag and no consumer state beside them.";
            ze:help "List the cached BGP UPDATE message IDs.";
        }
    }

    container request {
        config false;

        // The top-level request verb root, and this is the only module that
        // describes it. The summary names what every child does, because the
        // children come from a dozen owners: as112, bgp, cache, commit,
        // config, interface, l2tp, log, ospf, peer, quiesce and subscribe.
        // A summary naming the cache alone was false for the other eleven.
        description "This keyword runs nothing on its own. Thirteen modules merge their own children
onto it, and this module is the one that describes it.";
        ze:help "Commands that act on the running system.";

        container cache {
            config false;
            description "This keyword runs nothing on its own. Its four commands are retain, release,
expire and forward, and each one takes a cache entry ID. 'show cache' is what
lists the IDs.";
            ze:help "Manage cached BGP UPDATE messages.";

            container retain {
                config false;
                ze:command "ze-bgp:cache-retain";
                description "A retained entry is not evicted when it expires, so it stays listed until
'release' undoes the retain or 'expire' removes it. The ID leaf accepts a
comma-separated list, and each ID is acted on in turn with a failure reported
per ID.";
                ze:help "Prevent eviction of a cached message.";
                leaf id {
                    type string;
                    mandatory true;
                    description "One decimal cache entry ID, as show cache lists it, or several joined
by commas. A comma-separated value runs the action once for each ID and reports a
failure for each ID that is not in the cache. A value that is not a decimal
number is refused as an invalid cache id.";
                    ze:help "Cache entry ID, or a comma-separated list of IDs.";
                }
            }

            container release {
                config false;
                ze:command "ze-bgp:cache-release";
                description "The meaning depends on the caller. A cache consumer acknowledges the message and
does not forward it. An API caller undoes an earlier retain. The ID leaf
accepts a comma-separated list, and each ID is acted on in turn.";
                ze:help "Ack without forwarding (cache consumer) or undo retain (API).";
                leaf id {
                    type string;
                    mandatory true;
                    description "One decimal cache entry ID, as show cache lists it, or several joined
by commas. A comma-separated value runs the action once for each ID and reports a
failure for each ID that is not in the cache. A value that is not a decimal
number is refused as an invalid cache id.";
                    ze:help "Cache entry ID, or a comma-separated list of IDs.";
                }
            }

            container expire {
                config false;
                ze:command "ze-bgp:cache-expire";
                description "The entry is removed at once rather than when its lifetime ends. The ID leaf
accepts a comma-separated list, and each ID is acted on in turn with a failure
reported per ID.";
                ze:help "Remove a cached message immediately.";
                leaf id {
                    type string;
                    mandatory true;
                    description "One decimal cache entry ID, as show cache lists it, or several joined
by commas. A comma-separated value runs the action once for each ID and reports a
failure for each ID that is not in the cache. A value that is not a decimal
number is refused as an invalid cache id.";
                    ze:help "Cache entry ID, or a comma-separated list of IDs.";
                }
            }

        }
    }

    container send {
        config false;

        container bgp {
            config false;

            // No description on either container, and no selector leaf. The send
            // and bgp nodes are shared with ze-raw-cmd, which owns the text they
            // state and declares the selector every command below bgp inherits.

            container cached {
                config false;
                ze:command "ze-bgp:cache-forward";
                description "The ID leaf accepts a comma-separated list, and the selector applies to each
ID in that list. The command sends a message the cache already holds, so it names what
goes on the wire and not the act of sending it.";
                ze:help "Send a cached UPDATE to the peers the selector matches.";
                leaf id {
                    type string;
                    mandatory true;
                    description "One decimal cache entry ID, as show cache lists it, or several joined
by commas. A comma-separated value runs the action once for each ID and reports a
failure for each ID that is not in the cache. A value that is not a decimal
number is refused as an invalid cache id.";
                    ze:help "Cache entry ID, or a comma-separated list of IDs.";
                }
            }
        }
    }
}
