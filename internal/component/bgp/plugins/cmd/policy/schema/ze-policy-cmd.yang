module ze-policy-cmd {
    namespace "urn:ze:policy:cmd";
    prefix policycmd;
    import ze-extensions { prefix ze; }
    description "Policy chain inspection and dry-run testing commands. Owned by the BGP plugin because these handlers read per-peer policy chains and test UPDATE processing through the reactor. See ai/rules/plugin-self-containment.md.";
    revision 2026-06-06 { description "Relocated show policy chain/test out of the central show schema (plugin self-containment)."; }

    container show {
        config false;
        description "Read-only commands to inspect system, protocol, and network state";

        container policy {
            config false;
            description "Inspect and test route policy filters";

            container chain {
                config false;
                description "Show the effective filter chain for a peer";

                container peer {
                    config false;
                    ze:command "ze-show:policy-chain";
                    description "Show the import/export filter chain applied to a peer.
Usage: show policy chain peer <selector> [import|export]. The selector
(IP, name, as<N>) and the optional direction are parsed by the handler.
Shows the effective chain after group inheritance is resolved. Without
a direction keyword, shows both import and export.";
                }
            }

            container test {
                config false;
                description "Dry-run a BGP UPDATE through a policy chain (read-only, safe)";

                container peer {
                    config false;
                    ze:command "ze-show:policy-test";
                    description "Test what your policy does to a specific UPDATE.
Feed a hex-encoded BGP UPDATE through a peer's filter chain and see
the accept/reject result plus attribute modifications at each stage.
Read-only: no routes are actually forwarded. Great for validating
policy changes before you commit.
Usage: show policy test peer <selector> import|export [filter <name>]
update <hex> [source-asn4 true|false]. The selector and the
import/export/filter/update/source-asn4 tokens are parsed by the
handler so the peer selector can be a free-form name or address.";
                }
            }
        }
    }
}
