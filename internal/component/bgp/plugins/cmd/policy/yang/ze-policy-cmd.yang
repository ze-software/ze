module ze-policy-cmd {
    namespace "urn:ze:policy:cmd";
    prefix policycmd;
    import ze-extensions { prefix ze; }
    description "Policy chain inspection and dry-run testing commands. Owned by the BGP plugin because these handlers read per-peer policy chains and test UPDATE processing through the reactor. See ai/rules/plugin-self-containment.md.";
    revision 2026-08-30 { description "State filter, update and source-asn4 as keyword groups rather than leaves. Each is a keyword the operator types before its value, so a leaf published update as a bare positional the parser refuses, and the declaration order is what puts the chain being tested in front of the payload."; }
    revision 2026-08-29 { description "Declare the peer selector both policy commands read, and the filter, update and source-asn4 values show policy test peer takes as keyword pairs."; }
    revision 2026-06-06 { description "Relocated show policy chain/test out of the central show schema (plugin self-containment)."; }

    container show {
        config false;
        // No text on this container. ze-cli-show-cmd owns the show root and
        // states both halves, and a second module that restates one half is
        // what mergeHelpText reports as a mismatch.

        container policy {
            config false;
            description "This keyword runs nothing on its own. 'chain' reads the filter chain a peer has,
'test' feeds one UPDATE through it, and 'list', which ze-cli-show-cmd declares, names the
filter types available. All three are read-only.";
            ze:help "Inspect and test route policy filters.";

            container chain {
                config false;
                description "This keyword runs nothing on its own. 'peer' is its one branch, and the chain it
shows is the one left after group inheritance is resolved.";
                ze:help "Show the effective filter chain for a peer.";

                container peer {
                    config false;
                    ze:command "ze-bgp:show-policy-chain";
                    description "The selector
(IP, name, as<N>) and the optional direction are parsed by the handler.
Shows the effective chain after group inheritance is resolved. Without
a direction keyword, shows both import and export.";
                    ze:help "Show the import/export filter chain applied to a peer.";
                    leaf selector {
                        type string;
                        mandatory true;
                        description "The value is an IP address, a peer name, an AS pattern such as as65001,
or * for every peer. The chain of each peer it matches is shown.";
                        ze:help "Peer selector";
                    }

                    container direction {
                        config false;
                        ze:modifier "choice";
                        description "Without one, both halves are shown.";
                        ze:help "Which half of the chain to show.";
                        leaf direction {
                            type enumeration {
                                enum import { ze:help "Show the filters applied to the routes the peer sends."; }
                                enum export { ze:help "Show the filters applied to the routes sent to the peer."; }
                            }
                            description "The word follows the selector, and any other word there is refused.";
                            ze:help "The half of the chain to show.";
                        }
                    }
                }
            }

            container test {
                config false;
                description "This keyword runs nothing on its own. 'peer' is its one branch. Nothing is
forwarded and no route is installed, so the command is safe on a live router.";
                ze:help "Dry-run a BGP UPDATE through a policy chain (read-only, safe).";

                container peer {
                    config false;
                    ze:command "ze-bgp:show-policy-test";
                    description "Feed a hex-encoded BGP UPDATE through a peer's external policy chain and
see its final decision and attribute modifications. Named in-process protocol
checks are marked not-evaluated, not simulated; the result does not establish
that those checks would accept a live UPDATE. Selecting one as a single-filter
override is refused. Read-only: no routes are actually forwarded.
The selector and the direction, filter, update and source-asn4 tokens are
parsed by the handler, so the peer selector can be a free-form name or
address and the tokens can arrive in any order.";
                    ze:help "Test what your policy does to a specific UPDATE.";
                    leaf selector {
                        type string;
                        mandatory true;
                        description "The value is an IP address, a peer name, or an AS pattern such as
as65001. It MUST match exactly one peer: no match, and a match of several peers, are each
refused.";
                        ze:help "Peer selector";
                    }
                    // The handler refuses a call with no direction (errMissingDirection in
                    // handler.go), so this leaf is mandatory. Undeclared, positionalDef had
                    // no enum to bind the bare import or export token to and offered it to
                    // the filter leaf instead, which refused the documented form outright and
                    // silently read the direction as a filter NAME in the form it accepted.
                    leaf direction {
                        type enumeration {
                            enum import { ze:help "Feed the UPDATE through the peer's import chain."; }
                            enum export { ze:help "Feed the UPDATE through the peer's export chain."; }
                        }
                        mandatory true;
                        description "The word is required, and a call without it is refused. It picks which
of the peer's two chains the UPDATE is fed through.";
                        ze:help "Which half of the chain to test";
                    }
                    // A group rather than a leaf, and declared before update, because
                    // parsePolicyTestArgs reads `filter` as a keyword introducing the
                    // name. Declaration order is what puts the chain being tested in
                    // front of the payload fed through it.
                    container filter {
                        config false;
                        ze:modifier "once";
                        description "The keyword is accepted at most once, and the name runs from 1 to 64 characters.
Without it the whole chain is tested. A 'filter' keyword with no name after it
is refused.";
                        ze:help "Test one named filter instead of the whole chain.";
                        leaf name {
                            type string {
                                length "1..64";
                            }
                            mandatory true;
                            description "The value is the name of a filter in the peer's chain. The dry run
replaces the chain with that one filter. A name the chain does not carry is refused.";
                            ze:help "The filter to test on its own.";
                        }
                    }
                    // parsePolicyTestArgs answers errMissingUpdateHex when this is
                    // absent, so the handler has always required it. Declared as a
                    // leaf, the renderer published a bare positional and told an
                    // operator to type a hex string the parser refuses: the keyword
                    // introduces the value, so the model states a required group.
                    container update {
                        config false;
                        ze:modifier "required";
                        description "The keyword is required, and 'update hex <octets>' is accepted beside 'update
<octets>'. The octets take an optional 0x prefix. A keyword with no value after
it is refused.";
                        ze:help "The BGP UPDATE to feed through the chain.";
                        leaf hex {
                            type string {
                                pattern '(0[xX])?[0-9a-fA-F]+';
                            }
                            mandatory true;
                            description "The value is the whole BGP message, marker and header included, as hex
digits with an optional 0x prefix. It is at most 65535 bytes once decoded, and its type
byte MUST be 2. A body that does not parse as an UPDATE is refused.";
                            ze:help "The UPDATE octets, hex-encoded.";
                        }
                    }
                    container source-asn4 {
                        config false;
                        ze:modifier "once";
                        description "The value is 'true' or 'false', and the handler reads 'true' when the keyword is
absent. A value that is neither is refused. The keyword is accepted at most
once.";
                        ze:help "How to read the sender's AS support.";
                        leaf enabled {
                            type enumeration {
                                enum true { ze:help "Read AS_PATH with four-byte AS numbers, as a peer with the capability sends it."; }
                                enum false { ze:help "Read AS_PATH with two-byte AS numbers, as a peer without the capability sends it."; }
                            }
                            mandatory true;
                            description "It decides the width of each AS number in the AS_PATH and the
AGGREGATOR of the UPDATE, so the dry run decodes the attributes the way the named sender
encoded them.";
                            ze:help "Read the UPDATE as though the sender had four-byte AS support.";
                        }
                    }
                }
            }
        }
    }
}
