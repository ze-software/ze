module ze-cli-announce-cmd {
    namespace "urn:ze:cli:announce:cmd";
    prefix cliannouncecmd;
    import ze-extensions { prefix ze; }
    description "On-demand route origination and lifecycle management";
    revision 2026-09-05 { description "Every announce and withdraw form answers at one path, send bgp <selector>, and the two paths each had before are gone. The bare form is gone with them, so a form with no selector is refused and send bgp * is how an operator reaches every peer. The announce keyword is gone too: send is the verb, and to send a route IS to announce it, so the token after the selector names what goes on the wire (owner decision, 2026-09-05). withdraw stays, because a withdraw is the opposite act rather than the same act named twice, and it is the word RFC 4271 and ExaBGP both use. The root peer container is deleted: both its children moved and nothing else declared it."; }
    revision 2026-09-05 { description "This module states the text of the top-level peer container. ze-raw-cmd stated it while raw and update answered under that keyword, and both forms have moved to send bgp. No announce or withdraw form changes."; }
    revision 2026-09-01 { description "The two-path declaration is restored, and the flowspec traffic action is a one-of. A replay of an older upstream snapshot dropped the announce-forms and withdraw-forms groupings and the peer container, while ze-flowspec-cmd kept augmenting /cliannouncecmd:peer/announce/flowspec. That augment then resolved against nothing, so every config load failed and the daemon started for nobody. The one-of the same replay introduced is kept: community, rate-limit and discard are three spellings of the one extended community RFC 8955 Section 7 defines, an operator supplies exactly one, and the generated line bracketed all three as if the command ran without any. They sit in an action container carrying ze:modifier one-of, which the renderer states as a required alternation. The container's name is never typed."; }
    revision 2026-08-31 { description "Every announce and withdraw form is reachable at two paths. A bare form reaches every peer. peer <selector> announce and peer <selector> withdraw reach the peers the selector matches. That is the ExaBGP order an operator already types. Each set of forms is one grouping instantiated twice, so the second path restates no grammar. The selector is declared on the peer container the operator types it after. withdraw all loses its own selector leaf: the peer prefix states that scope for every form rather than one form stating it in its tail."; }
    revision 2026-08-30 { description "announce is three commands, one per form: unicast, blackhole and flowspec. The arguments after the form word differ between them, so one node could state at most one of the three and the description spelled the rest in prose. This is what withdraw was already split into. unicast and blackhole now state their whole grammar; flowspec states its trailing options only, because the match components are the flowspec NLRI plugin's vocabulary."; }
    revision 2026-08-29 { description "Declare the announce trailing groups: tag carries a key AND a value, so it is one group rather than two leaves, and for carries a duration whose keyword differs from its value name."; }
    revision 2026-08-29 { description "withdraw is three commands, one per form: tag, id and all. Each states its own arguments, so the grammar is in the model rather than in a handler's switch and in a description."; }
    revision 2026-06-27 { description "Initial revision"; }

    grouping announce-forms {
        description "The three announce forms. Each answers at one path, send bgp <selector>, with no announce keyword in front of it. The grouping stays because ze-flowspec-cmd augments the flowspec form and a grouping is what that augment resolves against.";

        container unicast {
            config false;
            ze:command "ze-bgp:announce-unicast";
            ze:rpc "ze-bgp-cmd-announce-api:announce";
            description "The address family follows the prefix, so it is ipv4 unicast or ipv6
unicast. The ORIGIN is IGP, and the next hop is this router unless next-hop names one.";
            ze:help "Originate a unicast route on demand.";
            leaf prefix {
                type string { length "1..49"; }
                mandatory true;
                description "The value is an IPv4 or IPv6 prefix with its length, such as 192.0.2.0/24.
The address family of the route follows from the prefix. A value that is not a prefix is
refused.";
                ze:help "Prefix to originate, in CIDR form";
            }

            container next-hop {
                config false;
                ze:modifier "once";
                description "It defaults to this router.";
                ze:help "The next hop to advertise.";
                leaf address {
                    type string { length "1..46"; }
                    mandatory true;
                    description "The value is an IPv4 or IPv6 address, or the word self. An IPv6 value MUST
be a global address, because the encoder adds the link-local half from the session. self
puts this router's own address in the NEXT_HOP.";
                    ze:help "An address, or self for this router";
                }
            }

            container community {
                config false;
                ze:modifier "repeat";
                description "The value is a standard community. Naming BLACKHOLE here meets
RFC 7999 Section 3.1 and its agreement gate. The fan-out then narrows to the sessions that
recorded the agreement.";
                ze:help "A community to attach, repeated for each one.";
                leaf value {
                    type string { length "1..32"; }
                    mandatory true;
                    description "The value is a standard community as ASN:value, such as 65000:100, or a
well-known name such as no-export or blackhole. Ze adds it to the COMMUNITIES attribute
of the route, and a value it cannot parse is refused.";
                    ze:help "Community, as ASN:value or a well-known name";
                }
            }

            container tag {
                config false;
                ze:modifier "once";
                description "The tag is what puts the announcement in the registry. Without a
tag the announcement is not tracked, so show announcements never lists it and withdraw id
cannot reach it. Each half is 64 characters at most.";
                ze:help "A key and a value carried with the announcement, so a later withdraw can name it.";
                leaf key {
                    type string { length "1..64"; }
                    mandatory true;
                    description "The value is free text of 64 characters at most. show announcements filters
on it, and withdraw tag names it to withdraw every announcement that carries it.";
                    ze:help "Tag key";
                }
                leaf value {
                    type string { length "1..64"; }
                    mandatory true;
                    description "The value is free text of 64 characters at most. withdraw tag names the
key and this value together to withdraw one group of announcements under a key.";
                    ze:help "Tag value";
                }
            }

            container for {
                config false;
                ze:modifier "once";
                description "The value is a Go duration such as 300s, or a whole number of
seconds. It needs no tag: an announcement given a lifetime enters the registry either way,
because that is where the timer lives, and the answer carries the id that withdraws it. An
announcement with a lifetime and no tag is reached by that id or by withdraw all, never by
a tag.";
                ze:help "How long the announcement lives before ze withdraws it.";
                leaf duration {
                    type string { pattern '([0-9]+(\\.[0-9]+)?(ns|us|ms|s|m|h))+|[0-9]+'; }
                    mandatory true;
                    description "The value is a Go duration such as 300s or 5m, or a whole number of seconds.
It MUST be more than zero. When it elapses Ze withdraws the announcement and removes it
from the registry.";
                    ze:help "Lifetime, in Go duration syntax or in whole seconds";
                }
            }
        }

        container blackhole {
            config false;
            ze:command "ze-bgp:announce-blackhole";
            ze:rpc "ze-bgp-cmd-announce-api:announce";
            description "This command attaches the BLACKHOLE community itself, so
RFC 7999 Section 3.1 narrows the fan-out to the sessions that recorded the
agreement.";
            ze:help "Originate a blackhole route on demand.";
            leaf prefix {
                type string { length "1..49"; }
                mandatory true;
                description "The value is an IPv4 or IPv6 prefix with its length, such as 192.0.2.1/32.
The address family of the route follows from the prefix. A value that is not a prefix is
refused.";
                ze:help "Prefix to blackhole, in CIDR form";
            }

            container tag {
                config false;
                ze:modifier "once";
                description "The tag is what puts the announcement in the registry. Without a
tag the announcement is not tracked, so show announcements never lists it and withdraw id
cannot reach it. Each half is 64 characters at most.";
                ze:help "A key and a value carried with the announcement, so a later withdraw can name it.";
                leaf key {
                    type string { length "1..64"; }
                    mandatory true;
                    description "The value is free text of 64 characters at most. show announcements filters
on it, and withdraw tag names it to withdraw every announcement that carries it.";
                    ze:help "Tag key";
                }
                leaf value {
                    type string { length "1..64"; }
                    mandatory true;
                    description "The value is free text of 64 characters at most. withdraw tag names the
key and this value together to withdraw one group of announcements under a key.";
                    ze:help "Tag value";
                }
            }

            container for {
                config false;
                ze:modifier "once";
                description "The value is a Go duration such as 300s, or a whole number of
seconds. It needs no tag: an announcement given a lifetime enters the registry either way,
because that is where the timer lives, and the answer carries the id that withdraws it. An
announcement with a lifetime and no tag is reached by that id or by withdraw all, never by
a tag.";
                ze:help "How long the announcement lives before ze withdraws it.";
                leaf duration {
                    type string { pattern '([0-9]+(\\.[0-9]+)?(ns|us|ms|s|m|h))+|[0-9]+'; }
                    mandatory true;
                    description "The value is a Go duration such as 300s or 5m, or a whole number of seconds.
It MUST be more than zero. When it elapses Ze withdraws the announcement and removes it
from the registry.";
                    ze:help "Lifetime, in Go duration syntax or in whole seconds";
                }
            }
        }

        container flowspec {
            config false;
            ze:command "ze-bgp:announce-flowspec";
            ze:rpc "ze-bgp-cmd-announce-api:announce";
            description "The match components come from ze-flowspec-cmd, which
augments this container. They are the FlowSpec codec vocabulary, and the plugin
that owns it declares them, so this module never restates another plugin's
words. An augmented container carries no declaration order, so the components
sort by name and land in front of the action and the options declared here.";
            ze:help "Originate a FlowSpec rule on demand (RFC 8955).";

            container action {
                config false;
                ze:modifier "one-of";
                description "RFC 8955 Section 7 makes it an extended community, so
the three containers below are three spellings of ONE community rather than
three mechanisms: community is the general case, and rate-limit and discard are
sugar over it. The operator types one of them and never types this container's
name.";
                ze:help "The traffic action, which every FlowSpec rule must carry.";

                container community {
                    config false;
                    ze:modifier "once";
                    description "rate-limit and discard are two spellings of this one
action.";
                    ze:help "The traffic action, as the extended community RFC 8955 Section 7 defines it.";
                    leaf value {
                        type string { length "1..64"; }
                        mandatory true;
                        description "The value is an extended community in the text form the configuration
reads, such as traffic-rate <asn> <rate> bytes or redirect <asn> <target>. It runs to the
tag or for keyword, so it can span several words. Ze attaches it to the FlowSpec rule as
its action.";
                        ze:help "Action community, such as traffic-rate or redirect";
                    }
                }

                container rate-limit {
                    config false;
                    ze:modifier "once";
                    description "It is sugar for a traffic-rate community.";
                    ze:help "Rate-limit the matched traffic.";
                    leaf bytes-per-second {
                        type string { pattern '[0-9]+'; length "1..20"; }
                        mandatory true;
                        description "The value is a whole number of bytes per second. Ze rewrites it as the
traffic-rate extended community with AS 0 and this rate.";
                        ze:help "Rate in bytes per second";
                    }
                }

                container discard {
                    config false;
                    ze:modifier "once";
                    description "It is sugar for a traffic-rate of zero.";
                    ze:help "Discard the matched traffic.";
                }
            }

            container tag {
                config false;
                ze:modifier "once";
                description "The tag is what puts the announcement in the registry. Without a
tag the announcement is not tracked, so show announcements never lists it and withdraw id
cannot reach it. Each half is 64 characters at most.";
                ze:help "A key and a value carried with the announcement, so a later withdraw can name it.";
                leaf key {
                    type string { length "1..64"; }
                    mandatory true;
                    description "The value is free text of 64 characters at most. show announcements filters
on it, and withdraw tag names it to withdraw every announcement that carries it.";
                    ze:help "Tag key";
                }
                leaf value {
                    type string { length "1..64"; }
                    mandatory true;
                    description "The value is free text of 64 characters at most. withdraw tag names the
key and this value together to withdraw one group of announcements under a key.";
                    ze:help "Tag value";
                }
            }

            container for {
                config false;
                ze:modifier "once";
                description "The value is a Go duration such as 300s, or a whole number of
seconds. It needs no tag: an announcement given a lifetime enters the registry either way,
because that is where the timer lives, and the answer carries the id that withdraws it. An
announcement with a lifetime and no tag is reached by that id or by withdraw all, never by
a tag.";
                ze:help "How long the announcement lives before ze withdraws it.";
                leaf duration {
                    type string { pattern '([0-9]+(\\.[0-9]+)?(ns|us|ms|s|m|h))+|[0-9]+'; }
                    mandatory true;
                    description "The value is a Go duration such as 300s or 5m, or a whole number of seconds.
It MUST be more than zero. When it elapses Ze withdraws the announcement and removes it
from the registry.";
                    ze:help "Lifetime, in Go duration syntax or in whole seconds";
                }
            }
        }
    }

    grouping withdraw-forms {
        description "The three withdraw forms. Each answers at one path, send bgp <selector> withdraw.";

        container tag {
            config false;
            ze:command "ze-bgp:withdraw-tag";
            ze:rpc "ze-bgp-cmd-announce-api:withdraw";
            description "A key of * withdraws every tagged announcement. An absent
value withdraws every value of the key.";
            ze:help "Withdraw the announcements carrying a tag.";
            leaf key {
                type string;
                mandatory true;
                description "The value is the key an announcement was made with, compared as text. Ze
withdraws each announcement made to the selector that carries it. A key of * withdraws every
tagged announcement made to the selector.";
                ze:help "Tag key, or * for every tagged announcement";
            }
            leaf value {
                type string;
                description "The value is the tag value an announcement was made with, compared as text.
With it, Ze withdraws the announcements under the key that carry this value alone. Absent,
or *, every value of the key is withdrawn.";
                ze:help "Tag value, or every value of the key when absent";
            }
        }

        container id {
            config false;
            ze:command "ze-bgp:withdraw-id";
            ze:rpc "ze-bgp-cmd-announce-api:withdraw";
            description "Only a tagged announcement carries an id. The withdraw acts
only when the selector typed after bgp is the one the announcement was made with, compared as
text.";
            ze:help "Withdraw one announcement by the id that show announcements reports.";
            leaf id {
                type string { length "1..20"; }
                mandatory true;
                description "The value is the whole number show announcements reports in its id column.
A value that is not a number is refused, and an id that names no announcement of the
selector answers 'not found'.";
                ze:help "Announcement id, as show announcements reports it";
            }
        }

        container all {
            config false;
            ze:command "ze-bgp:withdraw-all";
            ze:rpc "ze-bgp-cmd-announce-api:withdraw";
            description "The selector typed after bgp decides the scope: name a
peer to withdraw only the announcements made to it, or * for every one.";
            ze:help "Withdraw every on-demand announcement.";
        }
    }

    container send {
        config false;

        container bgp {
            config false;

            // No description on either container, and no selector leaf. The send
            // and bgp nodes are shared with ze-raw-cmd, which owns the text they
            // state and declares the selector every command below bgp inherits.
            // mergeYANGEntry warns when two modules describe one node differently.

            // The three announce forms sit directly under bgp. There is no
            // announce keyword, because send is already the verb and to send a
            // route IS to announce it (owner decision, 2026-09-05). The token
            // after the selector names WHAT goes on the wire.
            uses announce-forms;

            container withdraw {
                config false;
                description "Only a tagged announcement can be withdrawn by these forms, because an
announcement made without a tag leaves no registry entry. The three forms are tag, id and
all. The word stays where announce went, because a withdraw is the opposite act rather
than the same act named twice, and it is the word RFC 4271 and ExaBGP both use.";
                ze:help "Withdraw on-demand announcements.";
                uses withdraw-forms;
            }
        }
    }

    container show {
        config false;

        container announcements {
            config false;
            ze:command "ze-bgp:show-announcements";
            ze:rpc "ze-bgp-cmd-announce-api:show-announcements";
            description "Each row carries the id, the tag, the family, the peer selector, the
source and the creation time. An expiry time is present only when the announcement was made
with for.";
            ze:help "List active on-demand announcements.";
            leaf tag {
                type string { length "1..64"; }
                description "The value is a tag key, compared as text with the key each announcement was
made with. Absent, announcements of every key are listed.";
                ze:help "Show only announcements carrying this tag key";
            }
            leaf selector {
                type string;
                description "The value is compared as text with the selector the announcement was made
with, so it MUST be spelled the way that announcement spelled it. Absent, announcements to
every selector are listed.";
                ze:help "Show only announcements whose peer selector matches this pattern";
            }
            leaf family {
                type string { length "1..32"; }
                description "The value is an address family as the family column reports it, such as
ipv4/unicast. Absent, announcements of every family are listed.";
                ze:help "Show only announcements of this address family";
            }
        }
    }
}
