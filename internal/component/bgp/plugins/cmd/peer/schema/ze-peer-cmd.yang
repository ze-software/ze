module ze-peer-cmd {
    namespace "urn:ze:peer:cmd";
    prefix peercmd;
    import ze-extensions { prefix ze; }
    description "BGP peer operations: show, delete, and control peer sessions. Owns the show bgp-health overview and the delete bgp peer command surface; container-merges onto the show and delete verb roots.";
    revision 2026-03-16 { description "Initial revision"; }
    revision 2026-06-03 { description "Relocated show bgp-health and delete bgp peer out of the central show/delete schemas into this owner (plugin self-containment)."; }
    revision 2026-06-04 { description "Removed bare 'summary' and 'peer list' duplicates; moved summary under show bgp; canonical paths are 'show bgp summary' and 'show bgp peer list'."; }

    container show {
        config false;
        description "Peer inspection and diagnostics";

        container bgp {
            config false;
            description "BGP peers, sessions, RIB, and protocol tools";

            container summary {
                config false;
                ze:command "ze-bgp:summary";
                description "Show a one-line-per-peer BGP summary.
Lists every peer with state, ASN, prefixes received, and uptime.
Optionally scope by address family: ipv4, ipv6, or l2vpn.";
            }

            container peer {
                config false;
                description "Peer state, capabilities, statistics, history, and RIB views";

                container list {
                    config false;
                    ze:command "ze-bgp:peer-list";
                    description "List your peers, one line each.
Shows name, address, ASN, state, and uptime. Quick overview without
the detail of 'show bgp peer <selector> detail'.";
                }

                container detail {
                    config false;
                    ze:command "ze-bgp:peer-detail";
                    description "Show full detail for one or more peers.
Usage: show bgp peer <selector> detail. The selector can be an IP,
peer name, AS pattern (as65001), glob, or *.";
                    leaf selector { type string; mandatory true; description "Peer selector"; }
                }

                container capabilities {
                    config false;
                    ze:command "ze-bgp:peer-capabilities";
                    description "Show what capabilities were negotiated with a peer.
Usage: show bgp peer <selector> capabilities.";
                    leaf selector { type string; mandatory true; description "Peer selector"; }
                }

                container statistics {
                    config false;
                    ze:command "ze-bgp:peer-statistics";
                    description "Show UPDATE throughput for your peers.
Usage: show bgp peer <selector> statistics.";
                    leaf selector { type string; mandatory true; description "Peer selector"; }
                }

                container history {
                    config false;
                    ze:command "ze-bgp:peer-history";
                    description "Show FSM state transitions for a peer over time.
Usage: show bgp peer <selector> history.";
                    leaf selector { type string; mandatory true; description "Peer selector"; }
                }

                container rib {
                    config false;
                    ze:command "ze-bgp:peer-rib";
                    description "Show RIB data scoped to one peer.
Usage: show bgp peer <selector> rib [scope|filters|terminal].";
                    leaf selector { type string; mandatory true; description "Peer selector"; }
                }
            }
        }

        container bgp-health {
            config false;
            ze:command "ze-show:bgp-health";
            description "Quick health check for all your BGP peers.
Lists every peer with address, state, ASN, and uptime. Reports how
many are not Established. Much faster than 'show bgp peer *' when
you just need a status overview.";
        }
    }

    container delete {
        config false;
        description "Delete elements from the running configuration";

        container bgp {
            config false;
            description "Remove BGP peers from running config";

            container peer {
                config false;

                ze:command "ze-delete:bgp-peer";
                description "Remove a peer from the running config.
Tears down the TCP session and deletes the peer from the running
configuration. Does not modify the config file on disk.";
                leaf selector { type string; mandatory true; description "Peer selector"; }
            }
        }
    }

    container peer {
        config false;
        description "Peer lifecycle and flow control operations";
        ze:ui-resource "bgp-peer/index.html";
        ze:ui-permissions "network";
        ze:ui-csp "default-src 'self'";

        container teardown {
            config false;
            ze:command "ze-bgp:peer-teardown";
            description "Tear down a peer session.
Usage: peer <selector> teardown [cease-subcode].";
            leaf selector { type string; mandatory true; description "Peer selector"; }
        }

        container pause {
            config false;
            ze:command "ze-bgp:peer-pause";
            description "Pause reading from a peer's TCP socket.
Usage: peer <selector> pause.";
            leaf selector { type string; mandatory true; description "Peer selector"; }
        }

        container resume {
            config false;
            ze:command "ze-bgp:peer-resume";
            description "Resume reading from a previously paused peer.
Usage: peer <selector> resume.";
            leaf selector { type string; mandatory true; description "Peer selector"; }
        }

        container flush {
            config false;
            ze:command "ze-bgp:peer-flush";
            description "Wait until all queued updates for a peer are sent.
Usage: peer <selector> flush.";
            leaf selector { type string; mandatory true; description "Peer selector"; }
        }

        container plugin {
            config false;
            description "Plugin-level peer operations";

            container session {
                config false;
                description "Plugin session lifecycle";

                container ready {
                    config false;
                    ze:command "ze-plugin:session-peer-ready";
                    description "Signal that per-peer plugin setup is complete.
Usage: peer <selector> plugin session ready.";
                    leaf selector { type string; mandatory true; description "Peer selector"; }
                }
            }
        }
    }
}
