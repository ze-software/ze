module ze-peer-cmd {
    namespace "urn:ze:peer:cmd";
    prefix peercmd;
    import ze-extensions { prefix ze; }
    import ze-types { prefix zt; }
    // This module owns the show bgp health overview, and the create bgp peer
    // and delete bgp peer command surface. Its show, create and delete subtrees
    // container-merge onto the show, create and delete verb roots.
    description "BGP peer operations: create, show, delete, and control peer sessions.";
    revision 2026-10-23 { description "The request peer selector states which commands act on every peer it matches and which refuse all but one, delete bgp peer refuses a selector that is not one peer, disable states the communication Ze sends when no message is given, and teardown names RFC 9003."; }
    revision 2026-10-21 { description "clear bgp rib advertised withdraws the Adj-RIB-Out of the selected peers; show bgp health points at bgp-health in ze-bgp-api, its owner. request peer disable and enable hold a peer administratively down and release it. request peer notify closes a session with a NOTIFICATION of any code and subcode, its Data field given as text or, after the keyword hex, as octets."; }
    revision 2026-10-18 { description "The peer selector summary names * for every peer, so the selector guard's refusal, which quotes it, names the explicit every-peer form."; }
    // One verb pair for one runtime resource: create and delete, the pair the
    // verb table declares. peer-add and the delete verb's own spelling were
    // two names for one lifecycle, and Ze is unreleased, so both are renamed
    // outright, never aliased.
    revision 2026-10-09 { description "create bgp peer answers ze-bgp:peer-create and delete bgp peer ze-bgp:peer-delete, both declared in ze-bgp-api."; }
    // ze-bgp:peer-add was declared in ze-bgp-api.yang and no handler answered
    // it, so ze created no BGP peer at runtime while the schema published the
    // method to an operator and to an agent (ai/rules/principles.md).
    revision 2026-09-06 { description "Add create bgp peer, the runtime counterpart of delete bgp peer."; }
    // The model states both grammars and the renderer reproduces each line, so
    // the deleted prose stated a second time what the model already says.
    revision 2026-08-30 { description "Delete the usage sentences of show bgp peer rib and request peer teardown."; }
    // request peer teardown takes a cease subcode or it fails, because
    // handleTeardown refuses an empty tail. The description wrote the subcode as
    // optional and the model stated nothing. The peer selector of every command
    // under show bgp peer, update bgp peer and request peer moves to the peer
    // container, which is the keyword the operator types it after. show bgp peer
    // list reads every peer, so it states ze:inherit none.
    revision 2026-08-29 { description "State the required cease subcode, and move the peer selector to the peer container."; }
    revision 2026-03-16 { description "Initial revision"; }
    // They left the central show and delete schemas, for plugin
    // self-containment.
    revision 2026-06-03 { description "Relocated show bgp-health and delete bgp peer into this owner module."; }
    // summary moved under show bgp. The canonical paths are 'show bgp summary'
    // and 'show bgp peer list'.
    revision 2026-06-04 { description "Removed the bare 'summary' and 'peer list' duplicates."; }
    // 'show bgp' is the command that answers the peer summary, and the two views
    // are reached with the '| summary' and '| peers' pipe aliases.
    revision 2026-08-21 { description "Removed the 'summary' container under show bgp."; }

    // A comma-separated list is one token, so it survives the dispatcher's
    // keyword-value pass, which binds exactly one token to a keyword.
    typedef family-list {
        type string { pattern '[a-z0-9-]+/[a-z0-9-]+(,[a-z0-9-]+/[a-z0-9-]+)*'; }
        description "One or more AFI/SAFI names, comma separated (ipv4/unicast,ipv6/unicast).";
    }

    typedef process-list {
        type string { pattern '[a-zA-Z0-9_][a-zA-Z0-9_.-]*(,[a-zA-Z0-9_][a-zA-Z0-9_.-]*)*'; }
        description "One or more plugin process names, comma separated.";
    }

    container show {
        config false;

        container bgp {
            config false;
            ze:command "ze-bgp:overview";
            ze:rpc "ze-bgp-api:overview";
            description "Typed with no subcommand, lists every peer with state, ASN,
prefixes received, and uptime. Optionally scope by address family: ipv4, ipv6,
or l2vpn.";
            ze:help "BGP peers, sessions, RIB, and protocol tools.";

            container peer {
                config false;
                description "The mandatory peer selector is declared here, so every command below it reads
that one selector. 'list' is the exception: it declares ze:inherit none and
reads every peer. A selector is an address, a peer name, an AS pattern such as
as65001, a glob, or *.";
                ze:help "Peer state, capabilities, statistics, history, and RIB views.";

                // The peer every command below reads. It is declared here, on
                // the keyword the operator types it after, and each of those
                // commands inherits it. The selector can be an IP, a peer name,
                // an AS pattern (as65001), a glob, or *.
                leaf selector {
                    type string;
                    mandatory true;
                    description "The value is an IP address, a peer name, an AS pattern such as as65001, a
glob, or * for every peer. Every command under 'show bgp peer' reads the peers it matches,
except 'list', which reads every peer.";
                    ze:help "* for every peer, or an address, a peer name or an AS pattern";
                }

                container list {
                    config false;
                    ze:command "ze-bgp:peer-list";
                    ze:rpc "ze-bgp-api:peer-list";
                    ze:inherit "none";
                    description "Shows name, address, ASN, state, and uptime. Quick overview without
the per-peer detail.";
                    ze:help "List your peers, one line each.";
                }

                container detail {
                    config false;
                    ze:command "ze-bgp:peer-detail";
                    ze:rpc "ze-bgp-api:peer-show";
                    description "Each peer row carries the remote and local ASN, the router ID, the peer type,
'state' (the peer's lifecycle) and 'fsm-state' (the session's RFC 4271 Section 8.2.2
state, IDLE, ACTIVE, CONNECT, OPENSENT, OPENCONFIRM or ESTABLISHED),
and four timers: receive hold time, send hold time, keepalive, and connect
retry. The 'connect' and 'accept' flags say which directions this session opens.
A 'messages' map counts OPEN, UPDATE, NOTIFICATION, KEEPALIVE, ROUTE-REFRESH and
End-of-RIB in each direction. Negotiated nonzero PATHS-LIMIT values appear
under capabilities.paths-limit, keyed by family: send is the peer's maximum
paths per prefix enforced on our outbound updates; receive is our advertised
receive request, not a locally enforced inbound limit. Zero or absent limits
are omitted.";
                    ze:help "Show full detail for one or more peers.";
                }

                container capabilities {
                    config false;
                    ze:command "ze-bgp:peer-capabilities";
                    ze:rpc "ze-bgp-api:peer-show-capabilities";
                    description "The row carries the peer address and the FSM state. Once the OPEN exchange
completed, a negotiated map follows with the address families, the extended
message capability, enhanced route refresh, and 4-byte ASN support.
negotiated.paths-limit carries nonzero limits keyed by family: send is the
peer's maximum paths per prefix enforced on our outbound updates; receive is
our advertised receive request, not a locally enforced inbound limit. Zero or
absent limits are omitted. A selector that matches no peer is refused with
'no matching peers'.";
                    ze:help "Show what capabilities were negotiated with a peer.";
                }

                container statistics {
                    config false;
                    ze:command "ze-bgp:peer-statistics";
                    ze:rpc "ze-bgp-api:peer-show-statistics";
                    description "Each row carries the peer address, its ASN, the FSM state, and the session
uptime. Six counters follow, for UPDATE, KEEPALIVE and End-of-RIB messages in
each direction. Each rate is the cumulative counter divided by the uptime in
seconds, so a session that is not established reports 0.";
                    ze:help "Show UPDATE throughput for your peers.";
                }

                container history {
                    config false;
                    ze:command "ze-bgp:peer-history";
                    description "Each row reads as a sentence: when the transition happened, the state it left,
the state it reached, and the reason. Only the first matched peer is read, so a
wildcard selector with no argument is refused with 'no peer specified'. A peer
whose transitions were never recorded answers 'no history for peer'.";
                    ze:help "Show FSM state transitions for a peer over time.";
                }

                container rib {
                    config false;
                    ze:command "ze-bgp:peer-rib";
                    description "The command forwards to the RIB plugin with the peer selector attached, so the
RIB plugin MUST be loaded for it to answer. 'show bgp rib' reads the same plugin
without a peer scope.";
                    ze:help "Show RIB data scoped to one peer.";

                    container scope {
                        config false;
                        ze:modifier "choice";
                        description "Without one, routes sent and received are both shown.";
                        ze:help "Which direction of the peer's RIB to read.";
                        leaf scope {
                            type enumeration {
                                enum sent { ze:help "Read the routes Ze sent to the peer."; }
                                enum advertised { ze:help "Read the routes Ze sent to the peer, another spelling of sent."; }
                                enum received { ze:help "Read the routes the peer sent to Ze."; }
                                enum sent-received { ze:help "Read the routes of both directions, which is the default."; }
                            }
                            description "The word is typed first, before any pipe stage. The RIB plugin reads
its outbound table for sent, its inbound table for received, and both for sent-received.";
                            ze:help "Direction of the routes to read. 'advertised' is another spelling of 'sent'.";
                        }
                    }
                }
            }
            // The command node lives HERE, in the -cmd module, and not beside the
            // handler's other declarations in ze-bgp-cmd-peer-api.yang.
            // BuildCommandTree walks modules whose name ends -cmd alone
            // (cmdModuleSuffix), so a container declared in the -api module
            // produces no CLI path at all, and both dispatchers take their
            // "no path" branch and continue in SILENCE. The command was
            // unreachable from every entry point for exactly that reason.
            container update-delay {
                config false;
                ze:command "ze-bgp:update-delay";
                description "The command takes no argument, because the hold belongs to the speaker and not to a
peer. configured says an operator set bgp update-delay max-delay. holding says this speaker is withholding its
first advertisement right now, and released says the hold has ended. reason names the condition that ended it:
converged, establish-wait or max-delay. expected-peers, peers-held and peers-converged say what the hold is
still waiting for, so you can name the neighbor that has not finished. Read this command when a speaker has come
up and advertised nothing: it separates a hold that is working from a daemon that is wedged.";
                ze:help "Show the startup convergence hold and what it waits for.";
            }


            container health {
                config false;
                ze:command "ze-bgp:show-health";
                ze:rpc "ze-bgp-api:bgp-health";
                description "Lists every peer with address, state, ASN, and uptime. Reports how
many are not Established. Much faster than 'show bgp peer *' when
you just need a status overview.";
                ze:help "Quick health check for all your BGP peers.";
            }
        }
    }

    container create {
        config false;

        container bgp {
            config false;
            description "This keyword runs nothing on its own. 'create bgp peer <address> asn <asn>'
is the one command under it.";
            ze:help "Add BGP peers to the running daemon.";

            container peer {
                config false;

                ze:command "ze-bgp:peer-create";
                ze:rpc "ze-bgp-api:peer-create";
                description "The peer address and 'asn' are required. Every other keyword is
optional. Ze builds the peer, starts it, and dials the address unless 'connect
false' says otherwise. Ze writes nothing to the configuration file, and a
commit or a reload whose configuration does not declare the peer keeps it
running. 'delete bgp peer' is how it leaves, and it does not change the file on
disk either; 'update bgp config' writes the running peers to the file. An
address that already names a peer is refused, and so is a keyword Ze cannot
honor. Each name in 'attach' is bound to the whole surface: that process
receives every message from this peer and can send every type toward it. Write
the receive and send lists in the configuration file when the process needs
less.";
                ze:help "Add a peer to the running daemon.";

                // The leaf is named 'selector' because the dispatcher bridges
                // that ONE leaf name onto CommandContext.Peer (selectorLeaf in
                // internal/component/plugin/server/command.go), which is what
                // lets the operator type the address straight after 'peer'.
                // The type is an address rather than zt:peer-selector: a peer
                // that does not exist yet matches no glob, no name and no AS
                // pattern, so every other selector form names nothing here.
                leaf selector {
                    type zt:ip-address;
                    mandatory true;
                    description "The token typed after 'peer' is an IPv4 or IPv6 address and nothing else.
A name, a glob or an AS pattern is refused, because a peer that does not exist yet
matches none of them. An address that already names a peer is refused.";
                    ze:help "Address of the peer to create";
                }

                leaf asn {
                    type zt:asn-notated;
                    mandatory true;
                    description "The value is 1 to 4294967295, in asplain or asdot notation. Ze stores the
decimal form whichever notation you typed. AS 0 is refused, because RFC 7607 reserves it.";
                    ze:help "Remote AS of the peer, in any notation RFC 5396 names";
                }
                leaf local-as {
                    type zt:asn-notated;
                    description "The value is 1 to 4294967295, in asplain or asdot notation. Absent, the
session uses the router's own AS. AS 0 is refused.";
                    ze:help "Local AS for this session, overriding the router's, in any notation RFC 5396 names";
                }
                leaf local-address {
                    type zt:ip-address;
                    description "The value is an IPv4 or IPv6 address of this router. Ze binds the TCP
session to it. Absent, the kernel picks the source address.";
                    ze:help "Local address to bind the session to";
                }
                leaf router-id {
                    type zt:ipv4-address;
                    description "The value is a dotted quad and it MUST NOT be 0.0.0.0. Ze sends it as the
BGP Identifier in the OPEN for this session. Absent, the session uses the router's own.";
                    ze:help "BGP Identifier for this session, overriding the router's";
                }
                leaf receive-hold-time {
                    type uint16;
                    description "The value is 0 to 65535 seconds and Ze puts it in the Hold Time field of
its OPEN. The two peers then hold the lower of the two proposals. Absent, the value is 90.";
                    ze:help "Hold time in seconds (RFC 4271)";
                }
                leaf send-hold-time {
                    type uint16;
                    description "The value is 0 to 65535 seconds. A non-zero value MUST be at least 480 and
more than the receive hold time, or the peer is refused. 0 derives it as the larger of 480
and twice the receive hold time.";
                    ze:help "Send hold time in seconds, 0 for automatic (RFC 9687)";
                }
                leaf connect-retry {
                    type uint16;
                    description "The value is 0 to 65535 seconds and Ze reads it for a dynamic peer alone.
A disconnected dynamic peer is removed after this delay when no connection comes back. A
static peer reconnects on its own backoff, which this value does not change. Absent, the
value is 120.";
                    ze:help "ConnectRetry interval in seconds";
                }
                leaf connect {
                    type enumeration {
                        enum true { ze:help "Ze dials the peer."; }
                        enum false { ze:help "Ze does not dial the peer and waits for the peer to connect."; }
                    }
                    description "The value is true or false and nothing else. With false, the session comes
up only when the peer opens the TCP connection and 'accept' lets it in.";
                    ze:help "Dial the peer, default true";
                }
                leaf accept {
                    type enumeration {
                        enum true { ze:help "Ze answers a TCP connection the peer opens."; }
                        enum false { ze:help "Ze refuses a TCP connection the peer opens."; }
                    }
                    description "The value is true or false and nothing else. With false, the session comes
up only when 'connect' lets Ze dial the peer.";
                    ze:help "Accept a connection from the peer, default true";
                }
                leaf family {
                    type family-list;
                    description "Each name is an AFI/SAFI pair such as ipv4/unicast, and a name Ze does
not know is refused. Ze negotiates each family in the OPEN. Absent, the session uses the
configured default families.";
                    ze:help "Address families to negotiate, comma separated";
                }
                leaf graceful-restart {
                    type uint16;
                    description "The value is 0 to 4095 seconds. It is the Restart Time Ze advertises in
the graceful restart capability of its OPEN. Absent, the session advertises none.";
                    ze:help "Graceful restart time in seconds (RFC 4724)";
                }
                leaf group-updates {
                    type enumeration {
                        enum true { ze:help "Ze packs several NLRI that share path attributes into one UPDATE."; }
                        enum false { ze:help "Ze sends one prefix per UPDATE to this peer."; }
                    }
                    description "The value is true or false and nothing else. Packing reduces the number
of UPDATE messages from one per route to one per set of path attributes. Use false for a
peer that requires one prefix per UPDATE.";
                    ze:help "Group this peer's UPDATEs with other peers, default true";
                }
                leaf attach {
                    type process-list;
                    description "Each name is a plugin process the configuration declares. Ze binds the
peer to each one with the whole surface: the process receives every message from this peer
and can send every type toward it. An empty name is refused.";
                    ze:help "Plugin processes bound to this peer, comma separated";
                }
            }
        }
    }

    container delete {
        config false;

        container bgp {
            config false;
            description "This keyword runs nothing on its own. 'delete bgp peer <selector>' is the one
command under it.";
            ze:help "Remove BGP peers from running config.";

            container peer {
                config false;

                ze:command "ze-bgp:peer-delete";
                ze:rpc "ze-bgp-api:peer-delete";
                description "Tears down the TCP session and deletes the peer from the running
configuration. Does not modify the config file on disk.";
                ze:help "Remove a peer from the running config.";
                leaf selector {
                    type string;
                    mandatory true;
                    description "The value is an IP address, a peer name, an AS pattern such as as65001, a
glob. It names one peer: *, an exclusion such as !edge1, and a selector that
matches more than one peer are refused, and a pattern or glob that matches
exactly one peer is accepted. Ze tears down and deletes that peer.";
                    ze:help "One peer: its address or peer name";
                }
            }
        }
    }

    container update {
        config false;

        container bgp {
            config false;
            description "This keyword runs nothing on its own. 'update bgp peer <selector> prefix'
refreshes one peer's prefix maximums, and 'update bgp config' writes the running
peer set to the configuration file.";
            ze:help "BGP operational updates.";

            container peer {
                config false;
                description "The mandatory peer selector is declared here, so every command below it reads
that one selector. The one command under it writes to the configuration draft
and not to the running daemon, so 'config commit' is what applies the result.";
                ze:help "Per-peer data refresh.";

                // The peer every command below updates, declared on the keyword
                // the operator types it after.
                leaf selector {
                    type string;
                    mandatory true;
                    description "The value is an IP address, a peer name, an AS pattern such as as65001, a
glob, or * for every peer. 'prefix' refreshes the maximums of each peer it matches.";
                    ze:help "* for every peer, or an address, a peer name or an AS pattern";
                }

                container prefix {
                    config false;
                    ze:command "ze-bgp:update-peer-prefix";
                    description "Queries PeeringDB for each matched peer's ASN, applies the configured
margin, and writes the result to the config draft. Run 'config commit'
to apply.";
                    ze:help "Refresh max-prefix limits from PeeringDB.";
                }
            }

            // The node sits beside `peer` rather than under it, because the
            // command takes no selector: `update bgp peer` declares a mandatory
            // one that every node below it inherits, and the absence of a peer
            // is half of what this command persists.
            container config {
                config false;
                ze:command "ze-bgp:peer-save";
                ze:rpc "ze-bgp-api:peer-save";
                description "Ze writes the running peer set into the configuration file. A peer
'create bgp peer' built is added to the file, and a peer the file declares that
'delete bgp peer' removed is taken out of it. A peer both sides already hold is
left exactly as it was written. The running daemon does not change: the file is
brought to it. The command takes no selector, because after a delete no peer is
left to name and that absence is half of what the command persists. A created
peer is written under a name derived from its address, such as
'peer-192.0.2.7', because a peer name cannot start with a digit. The answer
names what was added, what was removed, and the file that was written.";
                ze:help "Write the running peer set to the configuration file.";
            }
        }
    }

    container clear {
        config false;

        container bgp {
            config false;

            container rib {
                config false;

                container advertised {
                    config false;
                    ze:command "ze-bgp:rib-clear-advertised";
                    ze:rpc "ze-bgp-api:rib-clear-advertised";
                    ze:task-support forbidden;
                    description "Withdraws every route the selected peers' sessions hold in their Adj-RIB-Out,
configured routes included, and the peers are left with nothing from Ze until
routes are announced again. clear bgp rib out resends the same table instead.
The selector is mandatory: clear bgp rib advertised alone is refused, and * is
the explicit form for every peer. A family typed after its keyword, as family
ipv4/unicast, limits the withdrawal to that family.";
                    ze:help "Withdraw every route advertised to a peer.";

                    leaf selector {
                        type zt:peer-selector;
                        mandatory true;
                        description "The value is an IP address, a peer name, an AS pattern such as as65001,
a glob, a comma-separated list of those, or * for every peer. A selector that
matches no peer is refused.";
                        ze:help "* for every peer, or an address, a peer name or an AS pattern";
                    }
                    leaf family {
                        type zt:address-family;
                        description "An address family such as ipv4/unicast. Absent, every family is withdrawn.";
                        ze:help "Address family to withdraw, such as ipv4/unicast";
                    }
                }
            }
        }
    }

    container request {
        config false;

        container peer {
            config false;
            description "The mandatory peer selector is declared here, and every command below it reads
that selector, including the ones ze-refresh-cmd.yang merges onto
this container. The web UI reaches the same operations at bgp-peer/index.html under
the 'network' permission.";
            ze:help "Peer lifecycle and flow control operations.";
            ze:ui-resource "bgp-peer/index.html";
            ze:ui-permissions "network";
            ze:ui-csp "default-src 'self'";

            // The peer every command below acts on. It is declared here, on the
            // keyword the operator types it after, and each of those commands
            // inherits it -- including the ones ze-refresh-cmd.yang merges onto
            // this container.
            leaf selector {
                type string;
                mandatory true;
                description "The value is an IP address, a peer name, an AS pattern such as as65001, a
glob, or * for every peer. 'refresh', 'borr', 'eorr' and 'flush' act on every peer
it matches. 'teardown', 'notify', 'disable', 'enable', 'pause', 'resume' and
'clear soft' act on one session: they refuse *, an exclusion such as !edge1,
and a selector that matches more than one peer, and they accept a pattern or
glob that matches exactly one peer.";
                ze:help "An address or peer name; * or a pattern for refresh, borr, eorr and flush";
            }

            container teardown {
                config false;
                ze:command "ze-bgp:peer-teardown";
                ze:rpc "ze-bgp-api:peer-teardown";
                description "The subcode is the NOTIFICATION subcode for error code 6 and it takes 0 to 255.
Ze sends an RFC 9003 Shutdown Communication with subcode 2, Administrative
Shutdown, and with subcode 4, Administrative Reset, and with no other subcode.
The message follows the subcode on the command line, and the answer echoes the
truncated text that went on the wire. With no message, Ze sends the subcode's
name, such as Administrative Shutdown, as the communication. The selector names
one peer: *, an exclusion and a selector matching several peers are refused.";
                ze:help "Tear down a peer session.";
                leaf cease-subcode {
                    type uint8;
                    mandatory true;
                    description "The value is a whole number from 0 to 255, and a value outside that range
is refused. Ze puts it in the Cease NOTIFICATION it sends before it closes the session.";
                    ze:help "BGP cease NOTIFICATION subcode";
                }
            }

            container notify {
                config false;
                ze:command "ze-bgp:peer-notify";
                ze:rpc "ze-bgp-api:peer-notify";
                description "Ze closes the session with a NOTIFICATION carrying the error code and error
subcode given, any value from 0 to 255. Under Cease (6), subcode 2 or 4, the
words after the subcode are the RFC 9003 Shutdown Communication; under every
other pair they are the Data field. Both are sent as UTF-8. With no words the
Data field is empty. A text that does not fit is refused and the session stays
up: more than 128 octets under Cease 2 or 4 (RFC 9003 Section 3), more than
4075 octets otherwise, or text that is not UTF-8. With the word hex after the
subcode, the next word is the Data field itself in hexadecimal, sent octet for
octet with no encoding, and refused over 4075 octets. teardown is the Cease-only
form; notify is the form for testing another implementation, and the hex form
is the one the ExaBGP bridge sends for teardown with a code.";
                ze:help "Close a peer session with a NOTIFICATION of any code and subcode.";
                leaf code {
                    type uint8;
                    mandatory true;
                    description "The NOTIFICATION error code, a whole number from 0 to 255.";
                    ze:help "NOTIFICATION error code";
                }
                leaf subcode {
                    type uint8;
                    mandatory true;
                    description "The NOTIFICATION error subcode, a whole number from 0 to 255.";
                    ze:help "NOTIFICATION error subcode";
                }
                // 8150 digits are the 4075 octets a NOTIFICATION's Data field
                // holds; the length lifts the 1024-byte cap every other
                // argument keeps (command.ValidateArgString).
                leaf hex {
                    type string { length "0..8150"; }
                    description "The Data field in hexadecimal, two digits for each octet, as one word typed
after the keyword hex in place of a text. It is sent as it is, so it can carry
octets that are not UTF-8 or a Shutdown Communication whose length octet is
wrong. More than 4075 octets, an odd number of digits, or a character other
than 0-9, a-f or A-F is refused.";
                    ze:help "Data field octets in hexadecimal";
                }
                // The text is free prose, so a word in it can name another
                // leaf ("the code is wrong"); ze:rest-of-line keeps every such
                // word in the text. Declared last: a client writes the leaves
                // in this order, and the text takes every word after it.
                leaf text {
                    type string { length "0..4075"; }
                    ze:rest-of-line;
                    description "Every word after the subcode, or after the keyword text, joined by one space.
No word in it is read as a keyword, so a text can hold the words code, subcode,
text or hex. Absent, the Data field is empty.";
                    ze:help "Data field text";
                }
            }

            container disable {
                config false;
                ze:command "ze-bgp:peer-disable";
                ze:rpc "ze-bgp-api:peer-disable";
                description "Ze closes a running session with Cease subcode 2, Administrative Shutdown,
and opens none until 'request peer <selector> enable'. The words after disable
are the RFC 9003 Shutdown Communication, and the answer echoes the text that
fits on the wire.";
                ze:help "Hold a peer administratively down.";
                leaf message {
                    type string;
                    description "Every word after disable, joined by one space. Absent, the Cease carries
Administrative Shutdown as its communication.";
                    ze:help "Shutdown communication";
                }
            }

            container enable {
                config false;
                ze:command "ze-bgp:peer-enable";
                ze:rpc "ze-bgp-api:peer-enable";
                description "Ze releases the hold of 'request peer <selector> disable' or of the peer
shutdown container, and the peer connects straight away. It takes no argument.";
                ze:help "Release a peer's administrative hold.";
            }

            container pause {
                config false;
                ze:command "ze-bgp:peer-pause";
                description "Ze stops reading the peer's socket and the session stays up, so nothing is
withdrawn. The selector resolves to one peer and a wildcard is refused, because
flow control acts on one read loop. 'request peer <selector> resume' restarts
it.";
                ze:help "Pause reading from a peer's TCP socket.";
            }

            container resume {
                config false;
                ze:command "ze-bgp:peer-resume";
                description "The read loop restarts after a flow-control pause. The selector resolves to one
peer and a wildcard is refused, for the reason pause states. Nothing else about
the session changes.";
                ze:help "Resume reading from a previously paused peer.";
            }

            container flush {
                config false;
                ze:command "ze-bgp:peer-flush";
                ze:rpc "ze-bgp-api:peer-flush";
                description "The command returns once the forward pool has drained, so a test asserts on what
the peer received without a fixed sleep. A selector of '*' flushes every peer.
The wait is bounded at 30 seconds.";
                ze:help "Wait until all queued updates for a peer are sent.";
            }

            container plugin {
                config false;
                description "This keyword runs nothing on its own. It groups the operations a plugin process
sends about one peer, and 'session' is its one branch.";
                ze:help "Plugin-level peer operations.";

                container session {
                    config false;
                    description "This keyword runs nothing on its own. 'ready' is its one branch, and it names
the moment a peer's plugin process finished its startup.";
                    ze:help "Plugin session lifecycle.";

                    container ready {
                        config false;
                        ze:command "ze-bgp:plugin-session-peer-ready";
                        ze:rpc "ze-plugin-api:session-peer-ready";
                        description "The daemon closes this sending process's share of the peer's
live-forward replay fence only for the captured peer-UP session token.
Missing, stale or retired process receipts fail without releasing queued work.
An explicit operator request is a no-op; it cannot credit a named process.
A peer of '*', and an empty peer, signal nothing.";
                        ze:help "Signal that per-peer plugin setup is complete.";
                        leaf session {
                            type string {
                                pattern '[1-9][0-9]*';
                            }
                            description "The opaque nonzero uint64 initial-replay token captured from
the peer-UP event whose replay this process finished. Never fetch a new token
to finish old replay work.";
                            ze:help "Captured peer-UP initial-replay token.";
                        }
                    }
                }
            }
        }
    }
}
