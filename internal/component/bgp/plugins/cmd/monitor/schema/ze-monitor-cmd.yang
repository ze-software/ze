module ze-monitor-cmd {
    namespace "urn:ze:monitor:cmd";
    prefix moncmd;
    import ze-extensions { prefix ze; }
    description "Live streaming commands that auto-refresh until you stop them";
    revision 2026-05-18 { description "Add monitor system netlink (kernel event streaming)"; }

    container monitor {
        config false;
        description "Continuous monitoring commands (Ctrl-C to stop)";

        container bgp {
            config false;
            ze:command "ze-bgp:monitor";
            ze:task-support required;
            description "Live BGP peer dashboard that refreshes automatically.
Shows all peers with state, uptime, and prefix counts. State changes
highlight as they happen. Ctrl-C to stop.";
        }

        container event {
            config false;
            ze:command "ze-event:monitor";
            ze:task-support required;
            description "Stream live events as they happen.
Shows a real-time feed of internal events. Filter with
include <pattern> or exclude <pattern> to focus on what matters.
Patterns match event type names.";
        }

        container ping {
            config false;
            ze:command "ze-monitor:ping";
            ze:task-support required;
            description "Continuous ping with live loss and RTT statistics.
Pings <target> until you stop it. Adjust interval and timeout as
needed. Shows running min/avg/max RTT and packet loss.";
        }

        container traceroute {
            config false;
            ze:command "ze-monitor:traceroute";
            ze:task-support required;
            description "Live mtr-style traceroute that updates continuously.
Shows each hop with running RTT statistics. Keeps probing so you
can watch path changes and latency shifts over time.";
        }

        container interface {
            config false;
            description "Interface traffic monitoring";

            container rate {
                config false;
                ze:command "ze-monitor:interface-rate";
                ze:task-support required;
                description "Stream per-second traffic rates for your interfaces.
Shows rx/tx bytes and packets per second, updating every second.
Optionally pass an interface name to watch just one link.";
            }
        }

        container system {
            config false;
            description "System-level event streams";

            container netlink {
                config false;
                ze:command "ze-monitor:system-netlink";
                ze:task-support required;
                description "Watch kernel networking changes in real time.
Streams netlink events: route adds/deletes, link state changes,
address assignments. Filter with route, link, address, or all.";
            }
        }

        container vpn {
            config false;
            description "VPN event streams";

            container ipsec {
                config false;
                ze:command "ze-monitor:vpn-ipsec";
                ze:task-support required;
                description "Watch IPsec SA events as they happen.
Streams sa-up, sa-down, child-up, child-down, and child-rekey
events. Useful for debugging tunnel flaps or rekey issues.";
            }
        }
    }
}
