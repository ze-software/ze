module ze-monitor-cmd {
    namespace "urn:ze:monitor:cmd";
    prefix moncmd;
    import ze-extensions { prefix ze; }
    description "monitor bgp command. Owned by the bgp-monitor plugin so that removing the BGP surface removes this node with its handler. The monitor verb root and all non-BGP monitor subcommands live outside this plugin (cmd/monitor and the per-feature owners). See ai/rules/plugin-self-containment.md.";
    revision 2026-06-03 { description "Trim to monitor bgp only; the verb root and non-BGP subcommands moved to cmd/monitor and per-feature owners."; }

    container monitor {
        config false;
        // No text on this container. ze-cli-monitor-cmd owns the monitor root
        // and states both halves, and a second module that restates one half
        // is what mergeHelpText reports as a mismatch.

        container bgp {
            config false;
            ze:command "ze-bgp:monitor";
            ze:rpc "ze-bgp-cmd-monitor-api:monitor";
            ze:task-support required;
            description "Shows all peers with state, uptime, and prefix counts. State changes
highlight as they happen. Ctrl-C to stop.";
            ze:help "Live BGP peer dashboard that refreshes automatically.";
        }
    }
}
