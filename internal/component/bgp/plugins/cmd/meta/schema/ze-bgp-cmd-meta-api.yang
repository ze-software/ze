module ze-bgp-cmd-meta-api {
  namespace "urn:ze:bgp:cmd:meta:api";
  prefix bgp-meta-api;

  organization "Ze Project";
  description
    "BGP command discovery, completion, and plugin configuration RPCs.";

  revision 2026-03-08 {
    description "Initial revision.";
  }

  rpc help { description "List bgp subcommands"; }
  rpc command-list { description "List bgp commands"; }
  rpc command-help { description "Show command details"; }
  rpc command-complete { description "Complete command/args"; }
  rpc event-list { description "List available BGP event types"; }
  rpc plugin-encoding { description "Set event encoding (json|text)"; }
  rpc plugin-format { description "Set wire format (hex|base64|parsed|full)"; }
  rpc plugin-ack { description "Set ACK timing (sync|async)"; }
}
