module ze-graceful-restart {
    namespace "urn:ze:graceful-restart";
    prefix gr;

    import ze-bgp-conf { prefix bgp; }

    description
        "Graceful Restart capability plugin for Ze (RFC 4724, code 64;
         RFC 9494, code 71). Configures per-peer restart-time for BGP
         graceful restart and long-lived-stale-time for LLGR.";

    revision 2025-01-31 {
        description "Initial revision.";
    }

    // Grouping for reuse across all augment paths
    grouping graceful-restart-config {
        container graceful-restart {
            presence "Graceful Restart capability enabled";
            description "Graceful Restart capability configuration.";

            leaf restart-time {
                type uint16 {
                    range "0..4095";
                }
                units "seconds";
                default "120";
                description
                    "Restart Time in seconds (RFC 4724 Section 3).
                     Maximum value is 4095 (12-bit field).";
            }

            leaf long-lived-stale-time {
                type uint32 {
                    range "0..16777215";
                }
                units "seconds";
                description
                    "Long-Lived Stale Time in seconds (RFC 9494 Section 3).
                     When set, LLGR capability (code 71) is advertised.
                     Maximum value is 16777215 (24-bit field, ~194 days).
                     Applied to all negotiated address families for the peer.";
            }
        }
    }

    // Standalone peer capability
    augment "/bgp:bgp/bgp:peer/bgp:capability" {
        uses graceful-restart-config;
    }

    // Peer inside group capability
    augment "/bgp:bgp/bgp:group/bgp:peer/bgp:capability" {
        uses graceful-restart-config;
    }

    // Group-level capability
    augment "/bgp:bgp/bgp:group/bgp:capability" {
        uses graceful-restart-config;
    }
}
