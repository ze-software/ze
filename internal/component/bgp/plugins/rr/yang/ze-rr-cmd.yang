module ze-rr-cmd {
    namespace "urn:ze:rr:cmd";
    prefix rrcmd;
    import ze-extensions { prefix ze; }
    description "show rr ... command tree. Owned by the bgp-rr plugin so that removing the route-reflector surface removes these command nodes together with the handlers. See ai/rules/plugin-self-containment.md.";
    revision 2026-06-03 { description "Relocated show rr ... out of the central show schema (plugin self-containment)."; }

    container show {
        config false;
        ze:help "Read-only commands to inspect system, protocol, and network state.";

        container rr {
            config false;
            description "A client is a peer this router reflects for, which is a configured relationship
                         rather than something negotiated with the peer.";
            ze:help "Route reflector status and client peers.";

            container status {
                config false;
                ze:command "ze-bgp:show-rr-status";
                description "Returns cluster ID, running state, and summary statistics
(reflected routes, client count).";
                ze:help "Show whether the route reflector is active.";
            }

            container peers {
                config false;
                ze:command "ze-bgp:show-rr-peers";
                description "Lists each RR client with session state and reflected route counts.";
                ze:help "Show route reflector client peers.";
            }
        }
    }
}
