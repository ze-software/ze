module ze-authz-conf {
    namespace "urn:ze:authz:conf";
    prefix authz;

    import ze-extensions { prefix ze; }

    description "Authentication and authorization configuration for Ze";

    revision 2026-01-01 {
        description "Initial revision";
    }

    container system {
        description "The container holds the system-wide settings. This module attaches the local user accounts under
                     authentication, and the command authorization profiles under authorization.";
        // Several modules declare this container and the config tree merges them,
        // so this text states what THIS module attaches under it.
        ze:help "System-level settings";

        container authentication {
            description "System authentication settings. The user list under it holds the local accounts, which the local
                         AAA backend reads. That backend runs after TACACS+ in the chain, so it answers when the remote
                         server is unreachable. A configuration with no user rejects every local login.";
            ze:help "System authentication settings";

            list user {
                key "name";
                description "Authenticated user (local). Each entry is one local account. password carries the bcrypt hash
                    the login compares against, and profile names the authorization profiles the account carries.
                    A commit rejects an entry whose name is reserved for a built-in identity.";
                ze:help "Authenticated user (local)";

                leaf name {
                    type string;
                    description "Username, and the key of this list. Ze matches the name a client presents at login
                        against this key. A commit rejects a reserved name, so an account cannot take the name of
                        the break-glass recovery identity.";
                    ze:help "Username";
                }

                leaf password {
                    type string;
                    ze:bcrypt;
                    description "The canonical form carries a cost prefix, for
                                 example $2a$10$ before the salt and the digest.
                                 Write the plaintext password to plaintext-password.
                                 On commit, ze hashes that value into this leaf and
                                 then discards the plaintext.";
                    ze:help "Bcrypt-hashed password, in canonical form.";
                }

                leaf plaintext-password {
                    type string;
                    ze:ephemeral;
                    ze:sensitive;
                    description "On commit, the config system hashes this value with
                                 bcrypt into the canonical password leaf, and it
                                 removes this leaf from the tree. Ze never writes the
                                 value to the config file. A display path renders the
                                 secret placeholder in its place.";
                    ze:help "Write-only plaintext password.";
                }

                leaf-list profile {
                    type leafref {
                        path "../../../authorization/profile/name";
                        require-instance true;
                    }
                    description "Authorization profile names assigned to this user. A commit rejects a name that no profile
                        under system authorization defines, naming the profiles that exist, and it rejects a reserved name. Once one profile
                        exists, a user with no name here authenticates and is then denied every command.";
                    ze:help "Authorization profile name(s) assigned to this user";
                }
            }
        }

        container authorization {
            description "Profile-based command authorization. Ze builds the authorization store only when this container
                         holds at least one profile. With no profile written, no store exists and every authenticated
                         user runs every command. The first profile therefore changes the answer for every user, and a
                         user with no profile assigned is denied from that point.

                         A backend that FAILS TO BUILD is dropped and the chain composes without it, so these
                         profiles still govern where the local backend survived. Where every backend fails,
                         nothing authenticates and every command is refused.";
            ze:help "Profile-based command authorization";

            list profile {
                key "name";
                description "Named authorization profile with a run section and an edit section. A user can carry several
                    profiles. Ze takes the action of the first profile that holds a matching entry. When no entry
                    of any profile matches, the section default of the first profile applies.";
                ze:help "Named authorization profile with run and edit sections";

                leaf name {
                    type string;
                    description "Profile identifier, and the key of this list. A user profile leaf-list, and a TACACS+
                        privilege level mapping, each name a profile by this key. A commit rejects a reserved name,
                        so a profile cannot take the name of a built-in identity.";
                    ze:help "Profile identifier";
                }

                container run {
                    description "Operational command authorization, which is the set of read-only commands. Ze evaluates this section when the dispatcher marks the command read-only, and the edit section for every other command.";
                    ze:help "Operational command authorization (read-only commands)";

                    leaf default-action {
                        type enumeration {
                            enum allow { ze:help "Permit a command that no entry of this section matches."; }
                            enum deny { ze:help "Refuse a command that no entry of this section matches."; }
                        }
                        description "Action when no entry of this section matches the command. Ze reads the value allow,
                            and it leaves the section at deny for every other state, the absent leaf included. A
                            user who carries several profiles falls back to the default of the first profile whose
                            section was reached.";
                        ze:help "Action when no entry matches";
                    }

                    list entry {
                        key "number";
                        description "Ordered authorization entry. Ze sorts the entries of the section by number and takes
                            the action of the first one that matches. A command that matches no entry falls to
                            default-action. An entry with an empty match is rejected at commit.";
                        ze:help "Ordered authorization entry";

                        leaf number {
                            type uint32;
                            description "Sequence number, and the key of this list. Ze sorts the entries by this number and
                                evaluates them in that order, so the number decides which entry wins. Write the
                                numbers with gaps, such as 10 and 20, to leave room for a later entry between
                                them.";
                            ze:help "Sequence number that orders this entry in the section.";
                        }

                        leaf action {
                            type enumeration {
                                enum allow { ze:help "Permit the command this entry matches and stop the search."; }
                                enum deny { ze:help "Refuse the command this entry matches and stop the search."; }
                            }
                            description "Authorization action for a command this entry matches. Ze reads the value allow, and
                                it leaves the entry at deny for every other state, the absent leaf included. The
                                first matching entry decides, so a deny stops the search even where a later entry
                                allows.";
                            ze:help "Authorization action";
                        }

                        leaf match {
                            type string;
                            description "Command path prefix, or a regular expression when regex is true. A prefix
                                comparison ignores case and stops at a word boundary. 'show bgp' therefore matches
                                'show bgp' and 'show bgp summary', and it does not match 'show bgpx'. An empty match
                                is rejected at commit. A match that names no command Ze knows is logged as a
                                warning and kept, because a plugin can register its commands later.";
                            ze:help "Command path prefix or regex pattern";
                        }

                        leaf regex {
                            type boolean;
                            description "If true, match is a regular expression. Ze compiles the pattern at commit and
                                rejects one it cannot compile. The pattern is not anchored, so it matches anywhere
                                inside the command text. Write ^ and $ where the whole command has to match. A regex
                                entry is case sensitive, unlike a prefix entry.";
                            ze:help "If true, match is a regular expression";
                        }
                    }
                }

                container edit {
                    description "Configuration command authorization, which is the set of commands that change the config. Ze evaluates this section for every command the dispatcher does not mark read-only.";
                    ze:help "Configuration command authorization (write commands)";

                    leaf default-action {
                        type enumeration {
                            enum allow { ze:help "Permit a command that no entry of this section matches."; }
                            enum deny { ze:help "Refuse a command that no entry of this section matches."; }
                        }
                        description "Action when no entry of this section matches the command. Ze reads the value allow,
                            and it leaves the section at deny for every other state, the absent leaf included. A
                            user who carries several profiles falls back to the default of the first profile whose
                            section was reached.";
                        ze:help "Action when no entry matches";
                    }

                    list entry {
                        key "number";
                        description "Ordered authorization entry. Ze sorts the entries of the section by number and takes
                            the action of the first one that matches. A command that matches no entry falls to
                            default-action. An entry with an empty match is rejected at commit.";
                        ze:help "Ordered authorization entry";

                        leaf number {
                            type uint32;
                            description "Sequence number, and the key of this list. Ze sorts the entries by this number and
                                evaluates them in that order, so the number decides which entry wins. Write the
                                numbers with gaps, such as 10 and 20, to leave room for a later entry between
                                them.";
                            ze:help "Sequence number that orders this entry in the section.";
                        }

                        leaf action {
                            type enumeration {
                                enum allow { ze:help "Permit the command this entry matches and stop the search."; }
                                enum deny { ze:help "Refuse the command this entry matches and stop the search."; }
                            }
                            description "Authorization action for a command this entry matches. Ze reads the value allow, and
                                it leaves the entry at deny for every other state, the absent leaf included. The
                                first matching entry decides, so a deny stops the search even where a later entry
                                allows.";
                            ze:help "Authorization action";
                        }

                        leaf match {
                            type string;
                            description "Command path prefix, or a regular expression when regex is true. A prefix
                                comparison ignores case and stops at a word boundary. 'show bgp' therefore matches
                                'show bgp' and 'show bgp summary', and it does not match 'show bgpx'. An empty match
                                is rejected at commit. A match that names no command Ze knows is logged as a
                                warning and kept, because a plugin can register its commands later.";
                            ze:help "Command path prefix or regex pattern";
                        }

                        leaf regex {
                            type boolean;
                            description "If true, match is a regular expression. Ze compiles the pattern at commit and
                                rejects one it cannot compile. The pattern is not anchored, so it matches anywhere
                                inside the command text. Write ^ and $ where the whole command has to match. A regex
                                entry is case sensitive, unlike a prefix entry.";
                            ze:help "If true, match is a regular expression";
                        }
                    }
                }
            }
        }
    }
}
