module ze-extensions {
    namespace "urn:ze:extensions";
    prefix ze;

    description "YANG extensions for ZeBGP config parsing syntax modes.
                 These extensions control how the config parser handles
                 nodes that need special syntax beyond standard YANG.";

    revision 2026-01-01 {
        description "Initial revision";
    }

    // Extension: listener
    // Marks a list entry as a network listener endpoint.
    // Used by port conflict detection (CollectListeners) to find all
    // services that bind to ip:port pairs. Applied to list nodes inside
    // service containers (e.g., web > server, ssh > server).
    extension listener {
        description "Marks a list entry as a network listener endpoint
                     for port conflict detection at config parse time.";
    }

    // Extension: syntax
    // Controls how the config parser handles this node.
    //
    // Values:
    //   flex           - accepts flag (;), value (word;), or block ({...})
    //   freeform       - accepts arbitrary words until ; or {}
    //   inline-list    - list with key + attributes on same line
    //   family-block   - special address family syntax (ipv4/unicast;)
    //   multi-leaf     - multiple space-separated values on one line
    //   bracket        - bracketed syntax [ a b c ] for leaf-list
    //   value-or-array - accepts either value; or [ a b c ];
    extension syntax {
        argument mode;
        description "Specifies the parsing syntax mode for this node.";
    }

    // Extension: flatten
    // Writes a container's children with the container name as a leading
    // keyword, so `attach { process foo { ... } }` is written and printed as
    // `attach process foo { ... }`. The parser accepts both spellings for
    // every container (automatic brace insertion); this extension makes the
    // flat one the form ze prints back.
    extension flatten {
        description "Serialize this container's children with the container
                     name as a leading keyword instead of a nested block.";
    }

    // Extension: key-type
    // For inline-list nodes, specifies the key type.
    //
    // Values: string, prefix, ip, uint32
    extension key-type {
        argument type;
        description "Specifies the key type for inline-list nodes.";
    }

    // Extension: route-attributes
    // Marker that this node accepts standard BGP route attributes.
    // Used on inline-list nodes for static/announce routes.
    extension route-attributes {
        description "Node accepts standard route attributes
                     (next-hop, origin, community, etc.)";
    }

    // Extension: ordered
    // Marks a leaf-list as an ordered SEQUENCE whose duplicate values are
    // meaningful, rather than a set. YANG leaf-lists are sets (RFC 7950 sec 7.7,
    // unique values), but a few BGP attributes are ordered sequences where
    // repeats are load-bearing: AS_PATH prepends (RFC 4271 sec 5.1.2) and MPLS
    // label stacks (RFC 8277). The parser preserves order AND duplicates for
    // these nodes instead of deduplicating.
    extension ordered {
        description "Marks a leaf-list as an ordered sequence whose duplicate
                     values are meaningful (AS_PATH prepends, MPLS label stacks),
                     so the parser preserves duplicates instead of treating the
                     leaf-list as a set.";
    }

    // Extension: allow-unknown-fields
    // Container accepts arbitrary key-value pairs beyond defined leaves.
    // Used for dynamic configuration like per-subsystem log levels.
    // Unknown fields are stored as key-value strings.
    extension allow-unknown-fields {
        description "Container accepts arbitrary unknown fields as strings.
                     Used for environment.log to allow subsystem paths
                     like 'bgp.routes debug;' for ze.log.bgp.routes=debug.";
    }

    // Extension: sensitive
    // Marks a leaf as containing sensitive data (passwords, keys).
    // Sensitive values are displayed as $9$-encoded in config output
    // and can be replaced with /* SECRET-DATA */ when private data is stripped.
    extension sensitive {
        description "Marks a leaf as containing sensitive data.
                     Values are obfuscated in display output using
                     JunOS-compatible $9$ encoding.";
    }

    // Extension: validate
    // References a registered Go function for runtime validation and completion.
    // Used only when YANG native constraints (enum, pattern, range) are insufficient —
    // primarily for runtime-determined valid sets (e.g., address families from plugins).
    // The argument is the validator function name registered via ValidatorRegistry.
    extension validate {
        argument name;
        description "References a custom validator function for runtime validation.
                     The function provides both Validate(path, value) and Complete()
                     for CLI tab-completion of valid values.";
    }

    // Extension: reference
    // Declares that a leaf or leaf-list names a configured entry that no
    // leafref path can express (for example a name that any of several lists
    // may hold). The argument names a source a component registers with
    // yang.RegisterReferenceSource. Editor completion offers exactly the names
    // the source lists at the leaf's position, and commit refuses any other
    // value, naming the leaf, the value and the configured choices. Use a
    // standard leafref with require-instance wherever a path fits.
    extension reference {
        argument source;
        description "Names the registered source whose names the leaf's value
                     MUST be one of. Completion and commit validation both
                     read it.";
    }

    // Extension: command
    // Marks a config false container as an executable command and references
    // the handler's WireMethod for dispatch (e.g., "ze-bgp:peer-list").
    // Without this extension, a config false container is just a grouping node
    // in the command tree (navigable but not executable).
    // The argument is the WireMethod string used for handler dispatch.
    extension command {
        argument handler;
        description "Marks a config false container as an executable CLI command.
                     The argument is the WireMethod (module:rpc-name) used for
                     handler dispatch. The YANG tree path defines the CLI hierarchy;
                     the handler argument connects it to the registered handler.";
    }

    // Extension: rpc
    // Points a ze:command node at the rpc statement that documents its input
    // and output. The node's ze:command argument is the one declaration of the
    // wire method; the rpc names no method of its own, so a module's file name
    // carries no meaning on the wire. Several nodes may point at one rpc, and
    // each publishes it under its own method. An rpc that no node points at,
    // and that declares no ze:method, is published under no name, and the
    // command contract gate refuses it
    // (internal/component/config/yang/rpc.go, PublishedRPCs).
    extension rpc {
        argument target;
        description "Names the rpc statement, as module:rpc-name, that documents
                     the input and output of this ze:command node. The rpc is
                     published under the node's wire method.";
    }

    // Extension: method
    // Declares the wire method of an rpc or a notification that no command
    // node reaches: the plugin IPC protocol and the event stream. These names
    // are an external contract, spelled on the wire exactly as written here.
    extension method {
        argument name;
        description "Declares the wire method of an rpc or notification that no
                     ze:command node points at, as module:name. The value is the
                     exact spelling on the wire.";
    }

    // Extension: help
    // Carries the SHORT summary of a command node, an rpc, a notification, a
    // config node or an enum value: one sentence a list row, a completion
    // candidate or a table cell can show whole. The YANG description statement
    // carries the LONG explanation, which a help page prints whole and the ?
    // box shows for a config node.
    //
    // The split is declared rather than derived. One string served both, and
    // each surface cut it differently: at the first sentence, at the first
    // newline, at 170 characters, or not at all. No cut can work, because 178
    // of the command tree's 653 nodes end in no punctuation and 354 are one
    // line.
    //
    // The description keeps the long form because it is the statement standard
    // YANG tooling reads and the schema output publishes, and a paragraph is
    // what a reader who opens the schema wants there. The summary is Ze's own
    // rendering concern, so it lives in Ze's own extension.
    //
    // The argument is one line of text. Every one-line surface reads it, and
    // the help page prints it as the heading above the description.
    //
    // Four carriers declare it. A config false container in a -cmd module
    // carries the CLI path an operator types, and mergeYANGEntry reads it
    // through Entry.Exts. An rpc carries the wire method that path reaches,
    // and ExtractRPCs reads it through gyang.RPC.Exts(). A config node carries
    // the setting an operator edits, and the CLI completer reads it through
    // Entry.Exts for the completion row. An enum value carries one choice of
    // a list key, and enumKeyVocabulary reads it through Enum.Extensions. One
    // reader answers all four
    // (internal/component/config/yang/command.go, GetHelpExtension).
    extension help {
        argument text;
        description "Declares the one-line summary of a command node, an rpc, a
                     notification, a config node or an enum value. The YANG
                     description statement declares the long explanation. This
                     statement declares the sentence that every list row,
                     completion candidate and table cell shows whole, and that
                     the help page prints as the heading above the explanation.";
    }

    // Extension: modifier
    // Marks a config false container as a trailing argument GROUP of its parent
    // command rather than a subcommand of its own: the operator supplies the
    // container's name and every leaf it declares together.
    //
    // Five occurrences, and each states one rendering:
    //
    //   once     [keyword <value>...]        supplied at most once
    //   repeat   [keyword <value>... ...]    supplied any number of times
    //   required keyword <value>...          supplied exactly once, no brackets
    //   choice   [word|word|word]            one of a closed set, or none
    //   one-of   (kw <value>|kw <value>)     exactly one of a closed set of GROUPS
    //
    // 'once' with NO leaf is a presence-only flag and renders `[keyword]`. That
    // is the form for a word the handler reads and reads no value after, such
    // as the `withdraw` of `debug ip ospf inject opaque`.
    //
    // 'required' is the mandatory sibling of 'once'. It is what states a
    // keyword that introduces a value the leaf name alone cannot spell:
    // `id <opaque-id>` is a container `id` holding a leaf `opaque-id`.
    //
    // 'choice' declares ONE leaf whose type states a closed set, and the
    // operator types one of those WORDS. The container's name is never typed;
    // it names the choice for a machine reader. `[import|export]` is that form.
    //
    // 'one-of' declares NO leaf and holds sibling containers instead, and the
    // operator supplies exactly one of them. It is what 'choice' cannot state:
    // a member carries its own keyword AND its own values, so a single word is
    // not enough to say it. `(community <value>|rate-limit <bytes-per-second>
    // |discard)` is that form. Round brackets say the group is required, since
    // square brackets say optional everywhere else on the line. Its own name is
    // never typed either, and neither completion nor help offers it: the
    // members take its place.
    //
    // A group with one value whose keyword IS the value's name earns no
    // extension at all: the renderer writes an optional leaf as `[name <name>]`
    // already.
    //
    // A container carrying ze:command is a subcommand whatever else it says, so
    // the two extensions never apply to the same container.
    extension modifier {
        argument occurrence;
        description "Marks a config false container as a trailing argument group
                     of its parent command. 'once' = at most once. 'repeat' =
                     any number of times. 'required' = exactly once, rendered
                     without brackets. 'choice' = one word from the closed set
                     its single leaf declares, or none. 'one-of' = exactly one
                     of the sibling groups it holds, each with its own keyword
                     and values. Any other argument is refused and the container
                     stays a plain grouping node.";
    }

    // Extension: rest-of-line
    // Marks a command's free-text string leaf as taking every word left on the
    // line, joined by one space. Without it the validator reads every word
    // that names a leaf as that leaf's keyword, so a text holding the word
    // "code" was refused under a command declaring a leaf named code. The leaf
    // starts at its own keyword, or at the first word typed once every
    // mandatory leaf is filled, and no word after that is read as a keyword
    // (command.ValidateArgs). Declare it last among the command's leaves: a
    // client writes the arguments in declaration order
    // (command.WriteInvocation), and every word after the leaf's keyword is
    // the leaf's.
    extension rest-of-line {
        description "Marks a command's string leaf as taking every word left on
                     the line, joined by one space, with no word in it read as a
                     keyword. At most one leaf of a command carries it, and only
                     a string leaf.";
    }

    // Extension: inherit
    // Says whether a command takes the values the containers ABOVE it declare.
    //
    // A container that names an object declares the leaf the operator types
    // after its keyword, once, and every command under it acts on that object:
    // `request interface <name> up`, `<name> down`, `<name> mtu <bytes>`. The
    // leaf lives on `interface` because that is the keyword it follows, and the
    // renderer places it there rather than after the last keyword.
    //
    // 'none' is for the command under such a container that acts on no single
    // member of the set: `show bgp peer list` reads them all, and `request
    // interface migrate` names two interfaces of its own. Without the
    // statement, the container's leaf would become a mandatory argument of
    // theirs and the bare command would be refused.
    extension inherit {
        argument mode;
        description "Says whether this command takes the leaves the containers
                     above it declare. 'none' = it takes none of them, because
                     it acts on no single member of the set the container names.
                     'ancestors' is the default and needs no statement. Any
                     other argument is refused and the command keeps the
                     default.";
    }

    // Extension: task-support
    // Declares whether an MCP tool is executed as a task.
    // Used by tools.go to populate execution.taskSupport in tools/list.
    // Values: "optional" (default), "required", "forbidden".
    //
    // The SERVER decides, per MCP 2026-07-28's io.modelcontextprotocol/tasks
    // extension: task creation is server-directed and this annotation is the
    // whole rule. Before that revision the CLIENT asked, per call, via
    // params.task, and these three words described what the client was allowed
    // to ask for. The vocabulary is unchanged because it always described the
    // command's relationship to task execution rather than who initiates it;
    // only the actor moved.
    extension task-support {
        argument level;
        description "Declares the MCP task-support level for this command.
                     Task creation is server-directed: the server decides from
                     this annotation, and the client opts in once by declaring
                     the io.modelcontextprotocol/tasks extension.
                     'required' = the server always returns a task handle,
                     'optional' = the call is synchronous (default if absent),
                     'forbidden' = the server never returns a task handle.";
    }

    // Extension: edit-shortcut
    // Marks a command as available in edit mode as a shortcut.
    // When typed in edit mode, implicitly runs as 'run <command>'.
    // Replaces the hardcoded editModeCommands map in model_mode.go.
    extension edit-shortcut {
        description "Marks a command as an edit mode shortcut.
                     Commands with this extension appear in edit mode completions
                     and execute as operational commands without requiring the
                     'run' prefix.";
    }

    // Extension: display-key
    // Marks a leaf in a keyless list as the display label for UI navigation.
    // The web interface uses this leaf's value as the entry name in the finder,
    // and shows it as an optional input when creating new entries.
    // If the leaf is empty, the UI falls back to child list keys or the index.
    extension display-key {
        description "Marks a leaf as the display label for keyless list entries.
                     The web interface reads this extension to determine which
                     leaf to show in navigation and prompt for on creation.";
    }

    // Extension: backend
    // Declares which interface/firewall/traffic backends implement this node.
    // The argument is a space-separated list of backend names (e.g.,
    // "netlink", "netlink vpp"). An absent `ze:backend` statement means the
    // node is supported by every registered backend for its component
    // (unrestricted). When the active backend is not in the list, the
    // commit-time feature gate rejects the config with a YANG-path diagnostic
    // instead of letting an Apply-time "not supported" error fire later.
    //
    // Consumers match on Keyword == "ze:backend" OR strings.HasSuffix on
    // ":backend" to accept both the long and short YANG prefixes.
    extension backend {
        argument names;
        description "Declares which backends implement this node. Argument is
                     a space-separated list of backend names (e.g.,
                     \"netlink\", \"netlink vpp\"). Absent = unrestricted.";
    }

    // Extension: os
    // Restricts a node to a specific operating system.
    // When the runtime OS does not match the argument, the node is excluded
    // from the schema -- it will not appear in config, CLI, or web UI.
    // The argument is a GOOS value. Valid values: linux, darwin, freebsd, openbsd, windows.
    // A typo silently hides the node on all platforms -- test after adding.
    extension os {
        argument goos;
        description "Restricts this node to the specified operating system.
                     Nodes with ze:os are excluded from the schema when
                     the runtime OS does not match.";
    }

    // Extension: cumulative
    // Marks a leaf-list as cumulative during config resolution.
    // Normal leaf-lists are replaced by more-specific config levels (peer > group > bgp).
    // Cumulative leaf-lists append values from all levels instead of replacing.
    // Used for filter tag/strip lists that must gather values across config hierarchy.
    extension cumulative {
        description "Marks a leaf-list as cumulative during config resolution.
                     Values from bgp, group, and peer levels are accumulated
                     (appended) instead of the most-specific level replacing others.";
    }

    // Extension: required
    // Declares a field path that must have a value in a list entry after
    // config inheritance resolution (bgp -> group -> peer merge).
    // Applied to list nodes. The argument is a slash-separated path
    // (e.g., "session/asn/remote"). Multiple ze:required statements
    // can appear on the same list.
    extension required {
        argument path;
        description "Declares a field that must have a value after config
                     inheritance resolution. Used for post-resolve validation
                     and to mark required fields in creation forms.";
    }

    // Extension: suggest
    // Declares a field path that should be shown in the creation dialog
    // but is not mandatory. Applied to list nodes. The argument is a
    // slash-separated path (e.g., "connection/local/ip").
    extension suggest {
        argument path;
        description "Declares a field to show in creation dialogs with
                     inherited defaults. Not mandatory -- the entry can
                     be created without it.";
    }

    // Extension: hidden
    // Marks a leaf as hidden from config display and the web editor.
    // Hidden leaves are stored in the config tree but not shown in the UI
    // or config output. Used for internal metadata fields (e.g., PeeringDB
    // update timestamps).
    extension hidden {
        argument value;
        description "Marks a leaf as hidden from config display and web editor.
                     The argument is a boolean string (true/false).";
    }

    // Extension: decorate
    // Attaches a display-time decorator to a leaf.
    // The argument names a registered decorator function (e.g., "asn-name").
    // When the web UI renders a decorated leaf, it calls the decorator to
    // obtain supplementary display text (e.g., AS number -> org name).
    extension decorate {
        argument name;
        description "Attaches a display-time decorator to a leaf.
                     The argument names a registered decorator function
                     that resolves supplementary display text for the value.";
    }

    // Extension: filter
    // Marks a list node as a named filter type for the route policy
    // framework. The policy registry (internal/component/policy) reads this
    // marker on the lists under the top-level policy container: a list that
    // carries it is a filter type and each entry is a named filter instance,
    // referenced by name in a filter { import/export } chain. A list without
    // it (policy routing's policy route) is never a filter type.
    extension filter {
        description "Marks a list under the top-level policy container as a
                     named filter type. Each entry is a filter instance that
                     an import or export chain references by name.";
    }

    // Extension: ephemeral
    // Marks a node as runtime-only. Ephemeral nodes are present in the
    // schema (validation and autocomplete work) but their values are not
    // persisted to the config file. Used for transient runtime state that
    // should not survive a restart.
    // Contrast with ze:hidden which hides from display but still saves.
    extension ephemeral {
        description "Marks a node as runtime-only. Values are validated
                     and autocompleted but not written to the config file.
                     Contrast with ze:hidden (hidden from display, saved).";
    }

    // Extension: related
    // Declares one operator tool related to the annotated config node.
    // Repeatable: multiple `ze:related` statements may appear on the same
    // node, each carrying one descriptor. The descriptor is encoded as a
    // single argument string with the wire format documented in
    // plan/spec-web-2-operator-workbench.md (Argument Wire Format):
    //
    //     id=peer-detail; label="Peer Detail"; \
    //     command="show bgp peer ${path:connection/remote/ip|key}"; \
    //     placement=row; presentation=drawer
    //
    // Field separator is `;`, key/value separator is `=`, and values that
    // contain `;`, `=`, `}`, or surrounding whitespace must be enclosed in
    // double quotes. Inside a quoted value `\"`, `\\`, and `\,` are the
    // only valid escapes; `\,` embeds a literal comma in list-valued
    // fields like `requires`.
    //
    // Required keys: id, label, command. Optional: placement (default
    // detail), presentation (default modal), confirm, requires, class,
    // empty (default disable). Unknown keys fail the schema build.
    //
    // ze:related is internal to ze and distinct from `ze:ui-resource`
    // (spec-mcp-5-apps.md), which advertises a static MCP UI bundle on a
    // command node. The two extensions intentionally do NOT share a
    // metadata model: ze:related annotates config nodes with executable
    // command templates plus placement/substitution metadata, while
    // ze:ui-resource annotates command nodes with a static asset URI for
    // sandboxed iframe rendering. See spec-web-2-operator-workbench.md
    // Design Decision D16 for the resolution rationale.
    extension related {
        argument descriptor;
        description "Declares one operator tool related to this node.
                     Argument is a single ;-separated key=value descriptor
                     (id, label, command required; placement, presentation,
                     confirm, requires, class, empty optional). Repeatable:
                     one descriptor per statement. Distinct from
                     ze:ui-resource (MCP Apps); see spec-web-2 D16.";
    }

    // Extension: ui-resource
    // Annotates a command-tree container with a UI resource bundle URI for
    // MCP Apps (2026-01-26). Applied to grouping containers (e.g., peer)
    // so the auto-generated MCP tool descriptor carries _meta.ui.resourceUri.
    // Argument is the relative path under the embedded ui/ FS (e.g.,
    // "bgp-peer/index.html"). The ui:// scheme prefix is added at runtime.
    extension ui-resource {
        argument path;
        description "Associates an embedded UI bundle with this command group.
                     Argument: relative path to the root HTML document under
                     internal/component/mcp/ui/. Applied to grouping containers.";
    }

    // Extension: ui-permissions
    // Declares the MCP Apps permissions array for a UI resource bundle.
    // Space-separated capability strings (e.g., 'network clipboard').
    extension ui-permissions {
        argument capabilities;
        description "Space-separated list of MCP App permission capabilities
                     advertised in _meta.ui.permissions.";
    }

    // Extension: ui-csp
    // Declares the Content-Security-Policy for a UI resource bundle.
    extension ui-csp {
        argument policy;
        description "CSP directive string advertised in _meta.ui.csp.";
    }

    // Extension: ensure-exists
    // Marks a command container as creating a resource that descendant commands
    // depend on. When the dispatcher executes a descendant command whose path
    // passes through this node, it first calls this node's handler to ensure the
    // resource exists (idempotent: succeeds if already present). If the
    // descendant command fails and this handler created the resource, the
    // dispatcher calls the rollback handler to clean up.
    //
    // The argument names the WireMethod of the undo/delete handler
    // (e.g., "ze-iface:interface-delete"). The dispatcher looks up this
    // handler at registration time to build the rollback chain.
    extension ensure-exists {
        argument rollback-handler;
        description "Marks a command container as a resource checkpoint.
                     Descendant commands auto-ensure this resource exists.
                     Argument: WireMethod of the rollback handler for undo
                     on descendant failure.";
    }

    // Extension: bcrypt
    // Marks a leaf as a one-way bcrypt-hashed value. Distinct from ze:sensitive
    // (which uses $9$ reversible obfuscation). Parser does NOT apply $9$ decode.
    // The companion commit hook (config.ApplyPasswordHashing) walks ze:bcrypt
    // leaves and bcrypt-hashes any plaintext-password sibling, populating this
    // leaf with the resulting hash. Canonical form is "$2a$10$...".
    extension bcrypt {
        description "Marks a leaf as one-way bcrypt-hashed. Parser preserves
                     value verbatim (no $9$ decode). Commit hook hashes any
                     sibling 'plaintext-<name>' leaf into this one.

                     Naming convention: the ephemeral input leaf MUST be named
                     'plaintext-<canonical>' (e.g., 'plaintext-password' next
                     to 'password'). The commit hook (config.ApplyPasswordHashing)
                     looks up the sibling by this exact prefix; a different
                     name silently disables auto-hash for that pair.";
    }
}
