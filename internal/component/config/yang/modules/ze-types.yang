module ze-types {
    namespace "urn:ze:types";
    prefix zt;
    import ze-extensions { prefix ze; }

    description "Common types for ZeBGP configuration";

    revision 2026-01-01 {
        description "Initial revision";
    }

    // Grouping for common route attributes used in announce/static/etc.
    grouping route-attributes {
        description "Common BGP route attributes";
        leaf next-hop {
            type string;
            ze:validate "nonzero-ipv4|literal-self";
            description "An IPv4 or IPv6 address, or the word self. The validator refuses 0.0.0.0.
                         The NEXT_HOP attribute (RFC 4271 Section 5.1.3) carries an IPv4 value, and
                         an IPv6 value travels in MP_REACH_NLRI.";
            ze:help "Next hop address";
        }
        leaf origin {
            type enumeration {
                enum igp { ze:help "Interior Gateway Protocol"; }
                enum egp { ze:help "Exterior Gateway Protocol"; }
                enum incomplete { ze:help "Incomplete origin"; }
            }
            description "One of igp, egp or incomplete. The value states how the route entered BGP,
                         and the ORIGIN attribute carries it as 0, 1 or 2.";
            ze:help "Origin attribute (RFC 4271 Section 4.3)";
        }
        leaf local-preference {
            type uint32;
            description "The LOCAL_PREF attribute (RFC 4271 Section 5.1.5), an integer that iBGP
                         peers compare first. A higher value is preferred.";
            ze:help "Local preference";
        }
        leaf med {
            type uint32;
            description "The MULTI_EXIT_DISC attribute (RFC 4271 Section 5.1.4), an integer that tells
                         an eBGP neighbor which entry point is preferred. A lower value wins.";
            ze:help "Multi-Exit Discriminator";
        }
        leaf-list community {
            type string;
            ze:validate "community-range";
            description "Each value is a standard community (RFC 1997), written as asn:value or as
                         one of the well-known names. The validator refuses a value outside the
                         16-bit range of each half.";
            ze:help "BGP communities";
        }
        leaf-list extended-community {
            type string;
            description "Each value is an extended community (RFC 4360), written as its type keyword
                         followed by the two fields, for example target:64500:100.";
            ze:help "Extended communities";
        }
        leaf-list large-community {
            type string;
            description "Each value is a large community (RFC 8092), written as three 32-bit integers
                         separated by colons, for example 64500:1:2.";
            ze:help "Large communities";
        }
        leaf-list as-path {
            type string;
            ze:ordered;
            description "The AS_PATH attribute (RFC 4271 Section 5.1.2). Each value is an ASN, and
                         the order is the order on the wire. The same ASN written twice is sent
                         twice, because a prepend is a meaningful repeat.";
            ze:help "AS path (ordered sequence; duplicate ASNs are meaningful prepends, not deduplicated)";
        }
        leaf path-information {
            type string;
            description "The ADD-PATH path identifier (RFC 7911), a 32-bit integer that tells two
                         routes to the same prefix apart.";
            ze:help "Path information";
        }
        leaf label {
            type string;
            description "One MPLS label for a labeled route (RFC 8277), as a decimal integer. Use
                         labels when the route carries a stack of more than one.";
            ze:help "MPLS label";
        }
        leaf-list labels {
            type string;
            ze:ordered;
            description "The label stack of a labeled route (RFC 8277), as decimal integers in the
                         order written. A label written twice is sent twice.";
            ze:help "MPLS labels (RFC 8277; ordered label stack, duplicates preserved)";
        }
        leaf rd {
            type string;
            description "The Route Distinguisher of a VPN route (RFC 4364), written as asn:number or
                         as ip:number. It is prepended to the prefix in the NLRI.";
            ze:help "Route Distinguisher";
        }
        leaf aggregator {
            type string;
            description "The AGGREGATOR attribute (RFC 4271 Section 5.1.7), written as asn:address.
                         It names the AS and the router that formed the aggregate.";
            ze:help "Aggregator attribute";
        }
        container atomic-aggregate {
            presence "Atomic aggregate flag";
            description "Present, the route carries the ATOMIC_AGGREGATE attribute (RFC 4271
                         Section 5.1.6). It tells a receiver that a less specific route was chosen.";
            ze:help "Atomic aggregate";
        }
        leaf originator-id {
            type ipv4-address;
            description "The ORIGINATOR_ID attribute, the router ID of the router that first
                         announced the route into the cluster. A route reflector sets it.";
            ze:help "Originator ID (RFC 4456)";
        }
        leaf cluster-list {
            type string;
            description "The CLUSTER_LIST attribute, the cluster IDs the route has crossed, written
                         as IPv4 addresses. A reflector that finds its own ID in it drops the route.";
            ze:help "Cluster list (RFC 4456)";
        }
        leaf name {
            type string;
            description "A label for the operator. It is stored beside the route and never reaches
                         the wire.";
            ze:help "Route name";
        }
        leaf split {
            type string;
            description "A prefix length, written as /24 or 24. The route is cut into every
                         prefix of that length that the announced prefix covers, and each one is
                         announced with the same attributes.";
            ze:help "Split horizon";
        }
        leaf watchdog {
            type string;
            description "The name of a watchdog pool. The route is tagged with that pool, so a
                         request bgp watchdog command announces or withdraws it with the rest.";
            ze:help "Watchdog name";
        }
        container withdraw {
            presence "Withdraw flag";
            description "Present, the route is withdrawn instead of announced. The other attributes
                         then only identify the route to withdraw.";
            ze:help "Withdraw flag";
        }
        leaf-list attribute {
            type string;
            description "A raw attribute, [ 0x<code> 0x<flags> 0x<value> ]: the type code, the flags
                         octet and the value, each written 0x and hex digits. Flags RFC 4271
                         Section 4.3 forbids a sender are refused. Use it for an attribute Ze has
                         no keyword for.";
            ze:help "Generic attributes";
        }
        container bgp-prefix-sid {
            presence "BGP Prefix SID enabled";
            description "Present, the route carries a BGP Prefix-SID attribute (RFC 8669), the
                         segment routing label index of the prefix.";
            ze:help "BGP Prefix SID";
        }
        container bgp-prefix-sid-srv6 {
            presence "SRv6 Prefix SID enabled";
            description "Present, the route carries a BGP Prefix-SID attribute with an SRv6 L3
                         Service TLV (RFC 9252), the SRv6 SID of the prefix.";
            ze:help "SRv6 Prefix SID";
        }
    }

    // Grouping for network listener endpoints (ip + port).
    // Used by all services that accept inbound connections.
    grouping listener {
        description "Common listener endpoint fields";
        leaf ip {
            type ip-address;
            description "The listener binds this address. 0.0.0.0 binds every IPv4 address of
                         the host, and :: binds every IPv6 address. On most services :: is
                         dual-stack: it also accepts IPv4 clients, so :: alone serves both
                         families. Config validation refuses two listeners that share a
                         protocol and a port when their addresses overlap. A wildcard address
                         overlaps every address of its own family, and a dual-stack :: also
                         overlaps every IPv4 address, so list :: alone rather than :: beside
                         0.0.0.0. A service whose IPv6 sockets are IPv6-only (L2TP, web)
                         accepts :: beside an IPv4 address on the same port.";
            ze:help "Listen IP address";
        }
        leaf port {
            type listener-port;
            description "The port range is 0 to 65535. Port 0 makes the operating system pick a
                         free port at bind time, so no client can know the port before the
                         listener starts. ze doctor tries to bind each configured endpoint and
                         reports the one the host refuses.";
            ze:help "Listen TCP port; 0 means OS-assigned";
        }
    }

    typedef node-name {
        type string {
            length "1..255";
            pattern "[a-zA-Z0-9_][a-zA-Z0-9_.-]*";
        }
        description "Configuration node name: ASCII alphanumeric, hyphens,
                     underscores, and dots. Must start with a letter, digit,
                     or underscore. Used for BGP peers/groups, firewall
                     tables/chains, interface units, sysctl profiles, and
                     other named config entries.";
    }

    typedef ip-address {
        type union {
            type ipv4-address;
            type ipv6-address;
        }
        description "IPv4 or IPv6 address";
    }

    typedef ipv4-address {
        type string {
            pattern '(([0-9]|[1-9][0-9]|1[0-9][0-9]|2[0-4][0-9]|25[0-5])\.){3}'
                  + '([0-9]|[1-9][0-9]|1[0-9][0-9]|2[0-4][0-9]|25[0-5])';
        }
        description "IPv4 address in dotted-decimal format";
    }

    typedef ipv6-address {
        type string {
            pattern '([0-9a-fA-F]{0,4}:){2,7}[0-9a-fA-F]{0,4}'
                  + '|([0-9a-fA-F]{0,4}:){1,6}:[0-9a-fA-F]{0,4}'
                  + '|::([0-9a-fA-F]{0,4}:){0,5}[0-9a-fA-F]{0,4}';
        }
        description "IPv6 address";
    }

    typedef asn {
        type uint32 {
            range "1..4294967295";
        }
        description "Autonomous System Number (4-byte, RFC 6793)";
    }

    typedef asn2 {
        type uint16 {
            range "1..65535";
        }
        description "Autonomous System Number (2-byte legacy)";
    }

    typedef asn-notated {
        type union {
            type asn;
            type string {
                pattern '[0-9]{1,5}\.[0-9]{1,5}';
            }
        }
        description "Autonomous System Number in any of the three notations RFC 5396 Section 2 names.
            An API leaf takes this type rather than asn. A command ACCEPTS asdot wherever an AS number is
            typed, and an answer WRITES asdot when bgp/as-notation selects it. The pattern here states the
            shape alone. Each field of the dotted form is range checked by asn.Parse, which every reader of
            an AS number goes through. A config leaf keeps type asn, because the tree stores the decimal
            value whatever the operator typed.";
    }

    typedef port {
        type uint16 {
            range "1..65535";
        }
        description "TCP/UDP port number";
    }

    // RFC 7950 Section 7.5.4.1: "If the constraint evaluates to "false", the
    // string is passed as <error-message> in the <rpc-error> in NETCONF." The
    // range carries the operator's message, so the first guard to refuse a VLAN
    // ID (the YANG range, ahead of any handler) speaks the reason and the fix.
    typedef vlan-id {
        type uint16 {
            range "1..4094" {
                error-message "IEEE 802.1Q reserves VLAN ID 0 and 4095, so a VLAN ID is 1 to 4094. Give a VLAN ID from 1 to 4094.";
            }
        }
        description "An IEEE 802.1Q VLAN ID. 0 and 4095 are reserved, so the range is 1 to 4094.";
    }

    typedef listener-port {
        type uint16 {
            range "0..65535";
        }
        description "TCP/UDP listener port number; 0 means OS-assigned";
    }

    typedef rate {
        type string {
            pattern '[0-9]+(bit|kbit|mbit|gbit|bps|kbps|mbps|gbps)';
        }
        description "Traffic rate string (for example 10mbit, 100kbit, 1gbps)";
    }

    typedef decimal-2 {
        type decimal64 {
            fraction-digits 2;
        }
        description "Decimal number with two fractional digits (for example 3.00).";
    }

    typedef ip-prefix {
        type union {
            type prefix-ipv4;
            type prefix-ipv6;
        }
        description "IPv4 or IPv6 prefix in CIDR notation";
    }

    typedef prefix-ipv4 {
        type string {
            pattern '(([0-9]|[1-9][0-9]|1[0-9][0-9]|2[0-4][0-9]|25[0-5])\.){3}'
                  + '([0-9]|[1-9][0-9]|1[0-9][0-9]|2[0-4][0-9]|25[0-5])'
                  + '/(([0-9])|([1-2][0-9])|(3[0-2]))';
        }
        description "IPv4 prefix in CIDR notation";
    }

    typedef prefix-ipv6 {
        type string {
            pattern '([0-9a-fA-F]{0,4}:){2,7}[0-9a-fA-F]{0,4}'
                  + '/([0-9]|[1-9][0-9]|1[0-1][0-9]|12[0-8])';
        }
        description "IPv6 prefix in CIDR notation";
    }

    typedef community {
        type string {
            pattern '[0-9]+:[0-9]+';
        }
        description "BGP standard community (AA:NN format)";
    }

    typedef large-community {
        type string {
            pattern '[0-9]+:[0-9]+:[0-9]+';
        }
        description "BGP large community (RFC 8092)";
    }

    typedef extended-community {
        type string {
            pattern '(target|origin):[0-9]+:[0-9]+';
        }
        description "BGP extended community (RFC 4360)";
    }

    typedef route-distinguisher {
        type string {
            pattern '([0-9]+:[0-9]+)|([0-9]+\.[0-9]+\.[0-9]+\.[0-9]+:[0-9]+)';
        }
        description "Route Distinguisher (Type 0 or Type 1)";
    }

    // IPC types

    typedef address-family {
        type string {
            pattern '[a-z0-9-]+/[a-z0-9-]+';
        }
        ze:validate "registered-address-family";
        description "AFI/SAFI string (e.g., ipv4/unicast, ipv6/unicast)";
    }

    typedef peer-selector {
        type string;
        description "Peer address, peer name, '*' for all, or comma-separated list";
    }

    typedef encoding-mode {
        type enumeration {
            enum text { ze:help "Human-readable text encoding"; }
            enum hex { ze:help "Hexadecimal encoding"; }
            enum b64 { ze:help "Base64 encoding"; }
        }
        description "Encoding mode for route data";
    }

    typedef wire-format {
        type enumeration {
            enum hex { ze:help "Hex bytes"; }
            enum base64 { ze:help "Base64 bytes"; }
            enum parsed { ze:help "Parsed JSON"; }
            enum full { ze:help "Full detail JSON"; }
        }
        description "Wire format for message output";
    }

    typedef ack-mode {
        type enumeration {
            enum sync { ze:help "Synchronous acknowledgment"; }
            enum async { ze:help "Asynchronous acknowledgment"; }
        }
        description "Acknowledgment mode for commands";
    }

    // IPC groupings

    grouping peer-info {
        description "Peer information returned by peer-list and peer-show";
        leaf address {
            type ip-address;
            description "The address the session is configured against, and the key of the answer.
                         The BGP component fills it from the peer table.";
            ze:help "Peer IP address";
        }
        leaf name {
            type string;
            description "The name the peer is configured under. The field is absent when the peer
                         has no name.";
            ze:help "Peer name (YANG list key)";
        }
        leaf group {
            type string;
            description "The name of the peer-group the peer inherits from. The field is absent for
                         a peer configured on its own.";
            ze:help "Peer-group name (empty if standalone)";
        }
        container remote {
            description "What the remote side of the session is. The BGP component fills it from
                         the peer configuration.";
            ze:help "Remote peer identity";
            leaf as {
                type asn;
                description "The autonomous system number the peer is configured with, as an
                             integer. It is the AS the OPEN message of the peer must carry.";
                ze:help "Peer ASN";
            }
        }
        container local {
            description "What this side of the session is. The BGP component fills it from the
                         peer configuration.";
            ze:help "Local identity for this peer";
            leaf as {
                type asn;
                description "The autonomous system number Ze sends in its OPEN message to this
                             peer, as an integer.";
                ze:help "Local ASN";
            }
            leaf address {
                type ip-address;
                description "The address Ze binds the TCP session to for this peer. It is the
                             source address of an outbound connection.";
                ze:help "Local bind address";
            }
        }
        leaf state {
            type string;
            description "The current state of the BGP finite state machine (RFC 4271 Section 8), in
                         lower case. Only established carries routes.";
            ze:help "FSM state (idle, connect, active, opensent, openconfirm, established)";
        }
        leaf router-id {
            type ipv4-address;
            description "The BGP identifier Ze uses on the session with this peer, as a dotted IPv4
                         address. It is the per-peer router-id when one is configured, and the
                         global one otherwise.";
            ze:help "Peer router ID";
        }
        leaf receive-hold-time {
            type uint16;
            description "The hold time in seconds configured for this peer, before negotiation with
                         the peer. The negotiated value is the smaller of the two sides.";
            ze:help "Configured receive hold time (RFC 4271)";
        }
        leaf send-hold-time {
            type uint16;
            description "The send hold time in seconds configured for this peer. A value of 0 means
                         Ze uses the larger of 8 minutes and twice the receive hold time.";
            ze:help "Configured send hold time (RFC 9687, 0=auto)";
        }
        leaf connect-retry {
            type uint16;
            description "The seconds Ze waits after a failed connection before it tries this peer
                         again. It is the ConnectRetryTimer of RFC 4271 Section 8.";
            ze:help "Connect retry interval";
        }
        leaf uptime {
            type uint32;
            description "The seconds since the session reached Established. It is 0 while the
                         session is in any other state.";
            ze:help "Seconds since established";
        }
    }

    grouping command-info {
        description "Command descriptor for introspection";
        leaf name {
            type string;
            description "The full command name, as an operator types it. The dispatcher fills it
                         from its builtin table.";
            ze:help "Command name";
        }
        leaf description {
            type string;
            description "The one-line summary of the command. It is the text the completion row
                         shows beside the name.";
            ze:help "Command help text";
        }
        leaf args {
            type string;
            description "The arguments the command accepts, as one usage string. It is empty when
                         the command takes none.";
            ze:help "Argument specification";
        }
        leaf source {
            type string;
            description "Where the command is registered. It is builtin for the dispatcher table,
                         and the plugin name for a command a plugin registered.";
            ze:help "Source (builtin or plugin name)";
        }
        leaf completable {
            type boolean;
            description "True when the CLI can offer the arguments of the command on tab, and
                         false when the operator types them with no help.";
            ze:help "Supports tab completion";
        }
    }

    grouping event-type-info {
        description "Event type descriptor for subscribe";
        leaf name {
            type string;
            description "The name subscribe takes to receive this event type. It is read from the
                         event registry of the namespace.";
            ze:help "Event type name";
        }
        leaf description {
            type string;
            description "The one-line text registered beside the event type, which says what the
                         event reports.";
            ze:help "Event description";
        }
    }

    grouping transaction-result {
        description "Result of a route transaction (commit-end)";
        leaf routes-announced {
            type uint32;
            description "The count of routes that left in UPDATE messages during the transaction,
                         summed over the peers.";
            ze:help "Routes announced";
        }
        leaf routes-withdrawn {
            type uint32;
            description "The count of routes withdrawn in UPDATE messages during the transaction,
                         summed over the peers.";
            ze:help "Routes withdrawn";
        }
        leaf updates-sent {
            type uint32;
            description "The count of UPDATE messages that left during the transaction. One message
                         can carry many routes, so it is not the route count.";
            ze:help "UPDATE messages sent";
        }
        leaf-list families {
            type address-family;
            description "The address families the transaction touched, one afi/safi pair each.";
            ze:help "Affected address families";
        }
    }

    grouping cache-entry {
        description "Cached BGP message descriptor";
        leaf message-id {
            type uint64;
            description "The identifier the cache assigned to the message. It is unique within the
                         cache, and a later command names the message with it.";
            ze:help "Cache message ID";
        }
        leaf peer {
            type ip-address;
            description "The address of the peer the message was received from.";
            ze:help "Source peer address";
        }
        leaf age-ms {
            type uint32;
            description "The milliseconds elapsed since the message entered the cache.";
            ze:help "Age in milliseconds";
        }
        leaf size {
            type uint32;
            description "The length of the message on the wire, in bytes, header included.";
            ze:help "Message size in bytes";
        }
    }

    typedef afi {
        type enumeration {
            enum ipv4 { value 1; ze:help "IPv4 (AFI 1)"; }
            enum ipv6 { value 2; ze:help "IPv6 (AFI 2)"; }
        }
        description "Address Family Identifier";
    }

    typedef safi {
        type enumeration {
            enum unicast { value 1; ze:help "Unicast (SAFI 1)"; }
            enum multicast { value 2; ze:help "Multicast (SAFI 2)"; }
            enum mpls { value 4; ze:help "MPLS-labeled (SAFI 4)"; }
            enum mpls-vpn { value 128; ze:help "MPLS VPN (SAFI 128)"; }
            enum flowspec { value 133; ze:help "FlowSpec (SAFI 133)"; }
        }
        description "Subsequent Address Family Identifier";
    }

    typedef dns-source-class {
        type enumeration {
            enum received {
                ze:help "Resolvers Ze learned from the network, by DHCPv4, DHCPv6, IPCP or router advertisement RDNSS.";
            }
            enum configured {
                ze:help "The resolvers configured on this consumer itself.";
            }
            enum self {
                ze:help "Ze's own address on the interface the client is on.";
            }
            enum radius {
                ze:help "The resolvers RADIUS gives one PPP subscriber.";
            }
        }
        description "The role of a source of DNS resolver addresses in a dns-source
                     list. A class names a role, never a protocol: every learned
                     protocol appears inside received, ordered by its registered rank.
                     Each consumer refuses the classes it cannot use.";
    }

    grouping dns-source {
        container dns-source {
            description "The ordered list of sources this consumer takes its DNS resolver
                         addresses from, and how it combines them. With the container
                         absent, the consumer uses its built-in default list, which its
                         own description states. Once any source is written, the default
                         no longer applies, its mode included.";
            ze:help "Where this consumer's DNS resolvers come from, and in what order.";

            leaf-list source {
                type dns-source-class;
                ordered-by user;
                description "The source classes in the order the consumer falls through
                             them. A class may appear once. Two or more classes need a mode:
                             Ze refuses the list without one, because it cannot tell whether
                             a later source is a backup or an addition.";
                ze:help "A source class, in fall-through order: received, configured, self, radius.";
            }

            leaf mode {
                type enumeration {
                    enum first-usable {
                        ze:help "The first source with a usable server wins; later ones are backups.";
                    }
                    enum merge {
                        ze:help "Every source's servers, in list order, each server listed once.";
                    }
                }
                description "How a list of two or more sources combines them. first-usable
                             takes the first source that holds a usable server and ignores
                             the rest; merge takes every source in list order. The leaf has
                             no default: a list naming one source needs none, and a list
                             naming more is refused without it.";
                ze:help "How two or more sources combine: first-usable or merge.";
            }

            leaf-list received-interface {
                type node-name;
                ordered-by user;
                description "Narrows the received source to the resolvers learned on these
                             interfaces, in this order, then by origin rank, then by unit.
                             With none listed, received takes every interface. Ze refuses
                             the leaf when the source list does not name received. An
                             interface that holds no lease yet is accepted: it may learn one
                             later.";
                ze:help "Take received resolvers only from these interfaces, in this order.";
            }
        }
    }
}
