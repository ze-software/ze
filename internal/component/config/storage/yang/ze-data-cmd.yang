module ze-data-cmd {
    namespace "urn:ze:data:cmd";
    prefix datacmd;
    import ze-extensions { prefix ze; }
    description "Live backup and config restore of the daemon's own store.";
    revision 2026-09-26 { description "Initial revision"; }

    container request {
        config false;

        container data {
            config false;
            description "These act on the running daemon's store. The file is on the daemon's host, and
                         the daemon reads or writes it under its own store lock.";
            ze:help "Back up the store, or restore a config from a backup.";

            container backup {
                config false;
                ze:command "ze-config:data-backup";
                description "Copies every key of the store into one blob artifact while the daemon runs. A
commit that lands meanwhile is in the backup whole or not at all. The file holds
credentials and private keys and is written 0600.";
                ze:help "Write a backup of the whole store to a file on the daemon's host.";
                leaf path {
                    type string { length "1..4096"; }
                    mandatory true;
                    description "Absolute path of the artifact. A relative path, a '..' element, a symlink, and
every name the store owns in its folder are refused, each naming the rule it
broke.";
                    ze:help "Absolute artifact path";
                }
                leaf spare {
                    type uint8 { range "0..100"; }
                    default 0;
                    description "Spare capacity in percent that each key and data slot carries. An artifact is
normally copied whole, so the default is 0.";
                    ze:help "Spare capacity percent (0-100)";
                }
                leaf force {
                    type empty;
                    description "Replace an existing file at path. It never lifts a refusal of a name the store
owns.";
                    ze:help "Replace an existing file";
                }
            }

            container restore {
                config false;
                ze:command "ze-config:data-restore";
                description "Stages the artifact's config as the candidate and runs the same reload a SIGHUP
runs. The config becomes active only when the reload accepts it; a refused
config leaves the active config and its pointers untouched. Nothing else in the
store changes. With client, a hub writes the config it serves to that managed
client instead, as a new version, and pushes config-changed to the client; the
hub does not reload its own config.";
                ze:help "Restore a config from a backup file on the daemon's host.";
                leaf path {
                    type string { length "1..4096"; }
                    mandatory true;
                    description "Absolute path of the artifact, checked before it is read by the same rules as a
backup path.";
                    ze:help "Absolute artifact path";
                }
                leaf config {
                    type empty;
                    description "Restore the artifact's config only. A full restore replaces the whole store
and runs offline with ze data restore.";
                    ze:help "Restore the config only";
                }
                leaf name {
                    type string { length "1..255"; }
                    description "The config to take from an artifact that holds several. Without it, the
artifact's only config, or the config named like this device, is taken.";
                    ze:help "Config name inside the artifact";
                }
                leaf client {
                    type string { length "1..64"; }
                    description "The managed client whose served config (client-<name>.conf) the restore
writes. The daemon MUST be a hub with a client entry of this name. Without it,
the restore replaces this daemon's own config through the reload.";
                    ze:help "Managed client whose served config is restored";
                }
            }
        }
    }
}
