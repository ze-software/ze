module ze-redistribute-conf {
    namespace "urn:ze:redistribute";
    prefix redist;

    import ze-extensions { prefix ze; }

    description "Route redistribution between protocols.
                 Protocols augment this container with their source types.
                 Hidden until redistribution is fully implemented.";

    revision 2026-04-09 {
        description "Initial revision";
    }

    container redistribute {
        ze:hidden true;
        description "Each destination protocol has its own container that holds the import
rules. To add a destination protocol, add a key here.";
        ze:help "Route redistribution between protocols.";

        list destination {
            key "protocol";
            description "Each entry names a protocol that declared itself a destination, for
example bgp or ospf.";
            ze:help "Destination protocol for redistributed routes.";

            leaf protocol {
                type string;
                // No ze:validate here. Each protocol declares its destination
                // name and the config root it needs from init()
                // (configredist.RegisterDestination), and the config doors
                // refuse a name no protocol declares, listing the declared
                // names, and a rule whose protocol has no block in the config
                // (config.RefuseRedistributeRules).
                description "bgp, ospf and isis are examples. A destination no protocol in this
build declares, or one whose protocol has no block in the config, is refused at
load, validate and commit.";
                ze:help "Name of the protocol that receives the redistributed routes.";
            }

            list import {
                key "source";
                description "With no filters and no final, Ze imports every route of the source.";
                ze:help "Import routes from a source into this destination.";

                leaf source {
                    type string;
                    ze:validate "redistribute-source";
                    description "ibgp, ebgp, static and connected are examples.";
                    ze:help "Name of the route source this rule imports from.";
                }

                leaf-list filters {
                    type string { length "1..max"; }
                    ordered-by user;
                    description "Run these filter instances, defined under the top-level policy root, in
order. Each one passes the route on, with what it sets, or rejects it. A filter of a type with no route
evaluator, or one reading a field a redistributed route does not carry, is refused. Select a family or a
tag with a match filter: match V4 { family [ ipv4/unicast ]; }.";
                    ze:help "Ordered filter instance references";
                    ze:reference "policy-filter";
                }

                leaf final {
                    type enumeration {
                        enum accept { ze:help "Import a route that passes every filter"; }
                        enum reject { ze:help "Do not import a route that passes every filter"; }
                    }
                    description "The decision after every filter passes. An import with filters must set it.
An import with neither filters nor final imports every route from the source.";
                    ze:help "Decision after every filter passes";
                }
            }
        }
    }
}
