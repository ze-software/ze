module ze-redistribute {
    namespace "urn:ze:redistribute";
    prefix redist;

    import ze-extensions { prefix ze; }

    description "Route redistribution between protocols.
                 Protocols augment this container with their source types.
                 Hidden until redistribution is fully implemented.";

    revision 2026-04-09 {
        description "Initial revision";
    }

    container redistribute {
        ze:hidden true;
        description
            "Route redistribution between protocols.
             Import routes from registered sources (ibgp, ebgp, static, connected, ...),
             optionally restricted to specific address families per source.";

        list import {
            key "source";
            description "Import routes from a source.
                         When family is omitted, all families are imported.";

            leaf source {
                type string;
                ze:validate "redistribute-source";
                description "Route source name (ibgp, ebgp, static, connected, ...)";
            }

            leaf-list family {
                type string;
                ze:validate "registered-address-family";
                description "Address families to import from this source.
                             Empty means all families.";
            }
        }
    }
}
