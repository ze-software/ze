module ze-redistribute-conf {
    namespace "urn:ze:redistribute";
    prefix redist;

    import ze-extensions { prefix ze; }

    description "Route redistribution between protocols.
                 Protocols augment this container with their source types.
                 Hidden until redistribution is fully implemented.";

    revision 2026-04-09 {
        description "Initial revision";
    }

    container redistribute {
        ze:hidden true;
        description
            "Route redistribution between protocols.
             Each destination protocol has its own container with import rules.
             Adding a new destination protocol means adding a new key here.";

        list destination {
            key "protocol";
            description "Destination protocol for redistributed routes.
                         Each entry names a registered consumer (bgp, ospf, ...).";

            leaf protocol {
                type string;
                // No ze:validate here: consumers register at plugin startup,
                // after YANG parse. Validated at runtime by the orchestrator.
                description "Destination protocol name (bgp, ospf, isis, ...)";
            }

            list import {
                key "source";
                description "Import routes from a source into this destination.
                             When family is omitted, all families are imported.";

                leaf source {
                    type string;
                    ze:validate "redistribute-source";
                    description "Route source name (ibgp, ebgp, static, connected, ...)";
                }

                leaf-list family {
                    type string;
                    ze:validate "registered-address-family";
                    description "Address families to import from this source.
                                 Empty means all families.";
                }
            }
        }
    }
}
