module ze-policy-conf {
    namespace "urn:ze:policy:conf";
    prefix policy;

    import ze-extensions { prefix ze; }

    description
        "The top-level policy root shared by Ze's route policy and policy
         routing. Each route policy filter type adds its list here through an
         augment and marks it ze:filter; policy routing adds its route list.";

    revision 2026-10-30 {
        description "Initial revision: the policy root moves out of bgp.";
    }

    grouping rib-import-chain {
        description "The import chain into the Loc-RIB, shared by every filter container that holds one.";
        container import {
            presence "Configure the import policy into the Loc-RIB.";
            description "A rejected route stays in the Loc-RIB as a hidden path that is never selected,
                         so relaxing the chain re-admits it without the protocol sending it again. The
                         source's chain runs first, then the rib chain.";
            ze:help "Import policy into the Loc-RIB";
            leaf-list filters {
                type string { length "1..max"; }
                ordered-by user;
                description "Run these filter instances in order. Each one passes the route on or
                             rejects it; a filter type with no Loc-RIB route evaluator is refused.";
                ze:help "Ordered filter instance references";
                ze:reference "policy-filter";
            }
            leaf final {
                type enumeration {
                    enum accept { ze:help "Accept a route that passes every filter"; }
                    enum reject { ze:help "Reject a route that passes every filter"; }
                }
                mandatory true;
                description "Every present import policy must set final accept or final reject, even with no filters.";
                ze:help "Decision after every filter passes";
            }
        }
    }

    grouping rib-import-filter {
        description "The import chain a route source, or the rib root for every source, applies at the
                     Loc-RIB. Declared once here and used by static, connected, ospf and rib.";
        container filter {
            description "A name references a filter instance defined under the top-level policy root. The
                         chain judges routes as they enter the Loc-RIB.";
            ze:help "Route filter chains into the Loc-RIB.";
            uses rib-import-chain;
        }
    }

    grouping igp-filter {
        description "The filter chains of a link-state IGP: the import chain into the Loc-RIB and the export
                     chain over what the IGP advertises from redistribution. Used by isis and ospf.";
        container filter {
            description "A name references a filter instance defined under the top-level policy root. The
                         import chain judges routes as they enter the Loc-RIB, and the export chain judges
                         redistributed routes before the IGP advertises them; the IGP's own database (an
                         IS-IS LSDB, an OSPF LSDB) is never filtered.";
            ze:help "Route filter chains into the Loc-RIB and out of redistribution.";
            uses rib-import-chain;
            container export {
                presence "Configure the export policy over redistributed routes.";
                description "Runs on every route the redistribute import rules hand this protocol, before it
                             enters the IGP database. A rejected route is not advertised; the sets of an
                             accepting chain (the metric, and on ospf the metric type and tag) shape what is.";
                ze:help "Export policy over redistributed routes";
                leaf-list filters {
                    type string { length "1..max"; }
                    ordered-by user;
                    description "Run these filter instances in order. Each one passes the route on or
                                 rejects it; a filter type with no route evaluator is refused.";
                    ze:help "Ordered filter instance references";
                    ze:reference "policy-filter";
                }
                leaf final {
                    type enumeration {
                        enum accept { ze:help "Advertise a route that passes every filter"; }
                        enum reject { ze:help "Do not advertise a route that passes every filter"; }
                    }
                    mandatory true;
                    description "Every present export policy must set final accept or final reject, even with no
                                 filters. A filter's accept only passes the route on, so final decides.";
                    ze:help "Decision after every filter passes";
                }
            }
        }
    }

    grouping route-source-conditions {
        description "The conditions on where a route came from, shared by the match filter and the
                     modify filter. Within one condition the values are alternatives; every condition
                     named must hold. A route that does not carry the field a condition reads fails it,
                     and an attachment whose routes never carry that field refuses the filter at load.";
        leaf-list protocol {
            type string { length "1..max"; }
            description "A route source registered by this build (static, connected, ospf, isis, bgp, ...),
                         or ebgp or ibgp for the class of a BGP best. An unknown name is refused at load.";
            ze:help "Match routes from this source";
        }
        leaf-list tag {
            type uint32;
            description "OSPF carries the external route tag and static carries its tag leaf. IS-IS carries
                         no administrative tag in Ze, so a filter reading tag is refused on an IS-IS chain.";
            ze:help "Match routes carrying this tag";
        }
        leaf-list level {
            type uint8 { range "1..2"; }
            description "The IS-IS level the route was selected at. Only IS-IS routes carry a level.";
            ze:help "Match IS-IS routes of this level";
        }
        leaf-list route-type {
            type enumeration {
                enum intra-area { ze:help "OSPF intra-area path"; }
                enum inter-area { ze:help "OSPF inter-area path"; }
                enum external-1 { ze:help "OSPF type 1 external path"; }
                enum external-2 { ze:help "OSPF type 2 external path"; }
                enum nssa-1 { ze:help "OSPF NSSA type 1 external path"; }
                enum nssa-2 { ze:help "OSPF NSSA type 2 external path"; }
            }
            description "The OSPF path type of RFC 2328 Section 11, with the NSSA types of RFC 3101.
                         Only OSPF routes carry a route type.";
            ze:help "Match OSPF routes of this path type";
        }
    }

    container policy {
        description "Each filter type is a list that its plugin adds through an augment and marks
                     ze:filter. An entry of such a list is a named filter instance, and an import or
                     export chain references it by name. One name belongs to one filter type only.
                     Policy routing adds its route list here too; a route entry is never a filter.";
        ze:help "Route policy filters and policy routing.";

        list match {
            ze:filter;
            key "name";
            description "With action accept, a route that meets every condition the instance names
                         passes on to the next filter and any other route is rejected; with action
                         reject, a route that meets them is rejected and any other passes on. An
                         instance is checked against only the
                         conditions it names, so one naming prefix-list and tag attaches to static, OSPF
                         and the rib chain, and is refused on IS-IS, whose routes carry no tag.";
            ze:help "Named route match filter instance.";
            leaf name {
                type string { length "1..max"; }
                description "A filter chain names this instance by this value.";
                ze:help "Match instance name, used in a filter chain.";
            }
            leaf action {
                type enumeration {
                    enum accept {
                        ze:help "Pass on routes meeting every condition, reject the rest.";
                    }
                    enum reject {
                        ze:help "Reject routes meeting every condition, pass on the rest.";
                    }
                }
                default accept;
                description "What happens to a route that meets every condition the instance names. The
                             other routes get the opposite.";
                ze:help "Accept or reject the routes this instance matches";
            }
            leaf-list family {
                type string { length "1..max"; }
                description "An address family name such as ipv4/unicast or ipv6/unicast.";
                ze:help "Match routes of this address family";
            }
            leaf-list next-hop {
                type string { length "1..max"; }
                description "An address prefix the route's next hop lies in, such as 192.0.2.0/24 or
                             2001:db8::1/128. A route with no next hop (connected) does not match.";
                ze:help "Match routes whose next hop is in this prefix";
            }
            leaf-list interface {
                type string { length "1..max"; }
                description "The outgoing interface the route names.";
                ze:help "Match routes through this interface";
            }
            container metric {
                description "The route's metric as its source states it: the SPF metric or cost of an IGP
                             route, a static route's configured metric. Either bound may be left out;
                             a minimum above the maximum is refused.";
                ze:help "Match routes whose metric is in this range";
                leaf minimum {
                    type uint32;
                    description "The lowest metric that matches, inclusive. Left out, the range starts at 0.";
                    ze:help "Lowest metric that matches";
                }
                leaf maximum {
                    type uint32;
                    description "The highest metric that matches, inclusive. Left out, the range ends at
                                 4294967295.";
                    ze:help "Highest metric that matches";
                }
            }
            uses route-source-conditions;
        }
    }
}
