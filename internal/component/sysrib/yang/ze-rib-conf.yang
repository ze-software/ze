module ze-rib-conf {
    namespace "urn:ze:rib:conf";
    prefix rib;

    import ze-extensions { prefix ze; }
    import ze-policy-conf { prefix policy; }

    description
        "System RIB configuration for Ze.
         The distance container controls cross-protocol route selection.
         Lower distance wins. It is the one declaration of every protocol's
         administrative distance.
         The fib-withhold leaf-list names the protocols whose selected routes
         are not programmed into the FIB.";

    revision 2026-09-08 {
        description
            "Add fib-withhold: the operator names the protocols whose routes
             stay out of the FIB. Selection and programming become separate
             stages.";
    }

    revision 2026-09-04 {
        description
            "Rename admin-distance to distance, and make this the only
             declaration: the bgp admin-distance container is deleted and every
             protocol reads its distance from here.";
    }

    revision 2026-04-04 {
        description "Add admin-distance container.";
    }

    container rib {
        uses policy:rib-import-filter;
        description "The system RIB takes the best route each protocol offers and
                     selects one system best for each prefix. The FIB plugins program
                     that winner into the kernel with netlink, into VPP, or into a P4
                     switch. The kernel FIB carries no administrative distance field, so
                     the ranking happens here and only the winner reaches netlink. The
                     distance container below is the one declaration of every protocol's
                     administrative distance. The fib-withhold leaf-list beside it names
                     the protocols whose winners are not programmed. Routes reach the
                     system RIB from the protocols, never from this block.";
        ze:help
            "System RIB configuration.";

        container distance {
            description "Administrative distance ranks one protocol against another for the same prefix, and the lower
                value wins. It is NOT an IGP metric and NOT the IGP distance to a next hop: those measure a path,
                this ranks the protocol that offered it. RFC 4271 mandates no values; these follow the Cisco and
                Juniper convention. This container is the only place any protocol's distance is declared, and every
                protocol takes its value from here whether or not you write the block.";
            ze:help "Administrative distance per protocol.";

            leaf connected {
                type uint8;
                default 0;
                description "A connected route is the prefix an interface address
                             covers. The default 0 is the best distance a route can
                             hold, so a connected route wins the prefix against every
                             protocol that carries a higher value. This is the only
                             distance leaf whose range starts at 0. The other five
                             start at 1. Raise it above another protocol's distance to let
                             that protocol win the same prefix. The value applies
                             whether or not you write the rib block, because sysrib
                             resolves every protocol from these schema defaults when it
                             starts.";
                ze:help
                    "Directly connected networks.";
            }

            leaf static {
                type uint8 {
                    range "1..255";
                }
                default 10;
                description "A static route is one the operator wrote under the static
                             configuration. The default 10 ranks a static route above
                             every dynamic protocol declared here and below a connected
                             route. The range is 1 to 255. The Loc-RIB ranks each static
                             route at this value unless the route carries its own
                             distance leaf, which wins over it. Raise it to more than 20 to let an eBGP route win the
                             same prefix.";
                ze:help
                    "Static routes.";
            }

            leaf ebgp {
                type uint8 {
                    range "1..255";
                }
                default 20;
                description "An eBGP route comes from a peer in another autonomous
                             system. The default 20 ranks eBGP above every IGP declared
                             here and below a static route. The range is 1 to 255. The
                             Loc-RIB looks this value up for each eBGP path when it
                             ranks it, so it decides selection before sysrib sees the
                             route, and a change re-ranks the routes already installed.";
                ze:help
                    "External BGP routes.";
            }

            leaf ospf {
                type uint8 {
                    range "1..255";
                }
                default 110;
                description "The default 110 ranks OSPF below eBGP and above IS-IS. The
                             range is 1 to 255. The Loc-RIB ranks each OSPF path at this
                             value when it ranks it, and a change re-ranks the routes
                             already installed. One value
                             covers every OSPF route: Ze declares no separate distance
                             for an external LSA.";
                ze:help
                    "OSPF routes.";
            }

            leaf isis {
                type uint8 {
                    range "1..255";
                }
                default 115;
                description "The default 115 ranks IS-IS below OSPF and above iBGP. The
                             range is 1 to 255. The Loc-RIB ranks each IS-IS path at
                             this value when it ranks it, and a change re-ranks the
                             routes already installed. One value covers level 1 and level 2: Ze
                             declares no separate distance for each level.";
                ze:help
                    "IS-IS routes.";
            }

            leaf ibgp {
                type uint8 {
                    range "1..255";
                }
                default 200;
                description "An iBGP route comes from a peer in the same autonomous
                             system. The default 200 is the highest of the six declared
                             here, so an iBGP route loses the prefix to any other
                             protocol that holds it. The range is 1 to 255. The Loc-RIB
                             ranks each iBGP path at this value when it ranks it. The eBGP distance is a separate leaf, so the
                             two BGP classes rank apart.";
                ze:help
                    "Internal BGP routes.";
            }
        }

        leaf-list fib-withhold {
            type string {
                length "1..64";
            }
            ze:validate "registered-protocol";
            description
                "This list names the protocols Ze does not program. Selection is
                 unchanged: the system RIB ranks the candidates for each prefix
                 on administrative distance and picks one winner. A winner from
                 a protocol named here stays in the RIB, `show rib` reports it,
                 redistribution can offer it to another protocol, and the
                 protocol's own event stream still carries it. Ze declines the
                 write to the kernel, to VPP or to a P4 switch. It holds the
                 prefix off `system-rib/best-change`, the stream every FIB
                 writer reads, so the list applies to every FIB. Ze also
                 releases the next-hop tracking for the prefix, so
                 `show nexthop-table` stops listing it under its next-hop.
                 An empty list withholds nothing, which is the behavior of a
                 router that says nothing here. Withholding is one of the
                 reasons a selected route is not programmed: a route the
                 operating system installs, and a route whose SRv6 SID reaches
                 nothing, are not written either. The values are the protocol
                 names this build registered: the editor completes them, and a
                 name nothing registered is refused at commit.";
            ze:help
                "Protocols whose selected routes are not programmed into the
                 FIB. An empty list programs all.";
        }
    }
}
