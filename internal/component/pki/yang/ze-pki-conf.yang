module ze-pki-conf {
    namespace "urn:ze:pki:conf";
    prefix pki;

    import ze-extensions { prefix ze; }

    description "PKI certificate store configuration for Ze.
                 Holds CA certificates and device certificates with
                 private keys. Used by IPsec, TLS, and other subsystems
                 that need X.509 identity.";

    revision 2026-09-08 {
        description "Stapled OCSP response on a device certificate, for RFC 9190 Section 5.4 (spec-ipsec-rfc9190).";
    }

    revision 2026-09-05 {
        description "CA revocation lists, for RFC 9190 Section 5.4 (spec-ipsec-rfc9190).";
    }

    revision 2026-05-19 {
        description "Initial PKI store (spec-ipsec-1).";
    }

    container pki {
        description "PKI certificate and key store. Presence of this block enables certificate-based authentication for
            IPsec VPN, TLS, and other subsystems.";
        ze:help "PKI certificate and key store.";

        list ca {
            key "name";
            description "Trusted CA certificate. The certificate leaf takes a PEM document, headers and line breaks
                included, which is what 'ze show pki local-ca pem' prints and what a .crt file holds. Base64-encoded
                DER with no PEM headers is also read.";
            ze:help "Trusted CA certificate.";

            leaf name {
                type string;
                description "The name is the list key, so one name holds one CA entry. Another block names this entry to
                    reach the trust anchor: an ipsec peer names it in ca-certificate, and a managed-client block
                    names it in ca. Ze takes letters, digits, dash, underscore and dot, up to 255 characters, and
                    refuses a config that holds any other character. An ipsec peer that names a CA this list does
                    not hold is refused at commit, so a typo never reaches a handshake.";
                ze:help "CA certificate name (referenced by consumers).";
            }

            leaf certificate {
                type string;
                mandatory true;
                description "The trust anchor itself, with no private key. Paste the PEM as it is printed, headers and
                    line breaks included, which is what 'ze show pki local-ca pem' gives you and what a .crt file
                    holds. Base64-encoded DER with no headers is also read, for a config written before PEM was
                    accepted.";
                ze:help "X.509 CA certificate, as a PEM document or as base64-encoded DER.";
            }

            leaf-list crl {
                type string;
                ordered-by user;
                description "Certificate revocation lists this CA issued, each an 'X509 CRL' PEM document or
                    base64-encoded DER. EAP-TLS on TLS 1.3 checks the revocation status of every certificate on a
                    peer's chain except the trust anchor. RFC 9190 Section 5.4 makes that check mandatory. An
                    EAP-TLS peer that validates against this CA and finds no current list here is refused. IKE
                    certificate authentication also checks every certificate on a peer's chain, except the trust
                    anchor, against the lists of each ca entry whose certificate is on that chain, once any such
                    entry holds a list: a revoked certificate, or one whose issuer has no current list, is refused.
                    An intermediate CA a peer's chain passes through is added as a ca entry with its own lists.
                    Publish a fresh list before the nextUpdate of the one here passes: an expired list answers
                    nothing about the present and refuses the same peers. A list that carries a critical extension
                    Ze cannot process (a delta CRL indicator, an issuing distribution point, a critical entry
                    extension) answers nothing either, per RFC 5280 Section 5.2. A list that revokes nothing is a
                    valid answer and is what a CA publishes while it has withdrawn no certificate.";
                ze:help "Certificate revocation lists this CA issued, each a PEM document or base64-encoded DER.";
            }
        }

        list certificate {
            key "name";
            description "One entry holds the certificate this device presents, the intermediate certificates that lead
                toward its trust anchor, and the private key that signs with it. The certificate leaf is mandatory
                and the private container is not, so an entry can hold a certificate Ze sends and cannot sign with.
                A TLS listener that asks for the key of such an entry is refused, and is never served another
                certificate in its place. Ze validates every entry when it loads the config. An expired certificate
                refuses the commit and stops the daemon from starting. A certificate that builds no chain to a ca
                entry in this block does the same.";
            ze:help "Device certificate with optional private key and
                     intermediate certificates.";

            leaf name {
                type string;
                description "The name is the list key, so one name holds one certificate entry. Another block names this
                    entry to present it: an ipsec peer in certificate, and a managed-client listener in certificate.
                    'show pki certificate name <name> pem' prints the entry under this name. Ze takes letters,
                    digits, dash, underscore and dot, up to 255 characters, and refuses a config that holds any
                    other character.";
                ze:help "Certificate name (referenced by consumers).";
            }

            leaf certificate {
                type string;
                mandatory true;
                description "The certificate this node presents. Paste the PEM as it is printed, headers and line
                    breaks included, which is what a .crt file holds. Base64-encoded DER with no headers is also
                    read, for a config written before PEM was accepted. The matching key goes in private key.";
                ze:help "X.509 device certificate, as a PEM document or as base64-encoded DER.";
            }

            leaf-list intermediate {
                type string;
                ordered-by user;
                description "Intermediate CA certificates, each a PEM document or base64-encoded DER. Give them in order, from the one that issued this
                    certificate toward the trust anchor. Ze stores them beside the device certificate for chain
                    building, and sends them after it in the IKE_AUTH chain. RFC 7296 Section 3.6 requires an
                    implementation be capable of being configured to send up to four X.509 certificates. This device
                    certificate plus three intermediates is that maximum. A single value is still valid.";
                ze:help "Intermediate CA certificates, from the issuer toward the trust anchor.";
            }

            leaf ocsp-response {
                type string;
                description "An OCSP response the certificate's issuer signed about this certificate, as base64-encoded
                    DER or as an 'OCSP RESPONSE' PEM document. Ze sends it in the certificate message when a peer
                    asks for a Certificate Status Request, which RFC 9190 Section 5.4 makes mandatory for an EAP-TLS
                    server on TLS 1.3. Fetch it from the responder your CA publishes, with 'openssl ocsp -respout'.
                    Ze refuses a response about another certificate. A response carries a nextUpdate: a peer that
                    checks the status refuses this certificate once that time passes, so replace the value before
                    it does. An entry with no response answers a Certificate Status Request with no status, which
                    RFC 6066 Section 8 permits, and the peer then checks revocation against the crl of the ca that
                    issued this certificate.";
                ze:help "OCSP response about this certificate, stapled to a peer that asks for it.";
            }

            container private {
                description "The container holds one leaf, key, and the container is optional. An entry with no private
                    key holds a certificate Ze sends and verifies against, and cannot sign with. Ze checks when it
                    loads the config that the key matches the public key of the certificate beside it. Ze refuses
                    the config when it does not, so a mismatched pair never reaches a handshake. The key leaf is
                    marked sensitive. The config file stores it as $9$, Ze decodes it on load, and a display path
                    prints a placeholder in its place.";
                ze:help "Private key associated with this certificate.";

                leaf key {
                    type string;
                    ze:sensitive;
                    description "Private key, as a PEM document or as base64-encoded DER. The config file stores it as $9$, and Ze
                        decodes it on load. The supported encodings are PKCS8, SEC1 (ECDSA), and PKCS1 (RSA).";
                    ze:help "Private key, as a PEM document or as base64-encoded DER.";
                }
            }
        }
    }
}
