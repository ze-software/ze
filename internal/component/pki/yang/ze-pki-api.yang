module ze-pki-api {
    namespace "urn:ze:pki:api";
    prefix pkiapi;

    import ze-extensions { prefix ze; }

    description "PKI API operations for Ze. RPCs for inspecting
                 loaded certificates and CA trust anchors.";

    revision 2026-05-19 {
        description "Initial PKI show commands (spec-ipsec-1).";
    }

    rpc certificates {
        description "Each row carries the name and the type, which is 'ca' or 'device'. The subject
and issuer common names follow, then the not-after date, the key algorithm, and
a 'valid' flag. The flag compares the not-after date against the clock alone, so
it does not say that the chain verifies. The rows are sorted by type and then by
name, and a 'count' comes with them.";
        ze:help "List all loaded certificates (CA and device).";
        output {
            leaf certificates {
                type string;
                description "One object per loaded CA or device certificate, sorted by type and
then by name. The array is empty when the store holds none.";
                ze:help "JSON array of certificate summary objects.";
            }
        }
    }

    rpc certificate {
        description "Sub-commands: pem, bundle pem, fingerprint
[sha256|sha384|sha512].";
        ze:help "Show details, PEM, bundle, or fingerprint of a named certificate.";
        input {
            leaf name {
                type string;
                description "The name a pki ca or pki certificate block declares. The CA store is
searched first, then the device store, and a miss fails with pki: certificate <name> not
found and the names that exist.";
                ze:help "Certificate name to look up.";
            }
        }
        output {
            leaf certificate {
                type string;
                description "The shape follows the sub-command: details as fields, the PEM as one
text block, or the digest as a colon-separated hex string.";
                ze:help "JSON object: certificate details, PEM text, or fingerprint
                         depending on sub-command.";
            }
        }
    }
}
