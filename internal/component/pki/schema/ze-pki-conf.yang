module ze-pki-conf {
    namespace "urn:ze:pki:conf";
    prefix pki;

    import ze-extensions { prefix ze; }

    description "PKI certificate store configuration for Ze.
                 Holds CA certificates and device certificates with
                 private keys. Used by IPsec, TLS, and other subsystems
                 that need X.509 identity.";

    revision 2026-05-19 {
        description "Initial PKI store (spec-ipsec-1).";
    }

    container pki {
        description "PKI certificate and key store.
                     Presence of this block enables certificate-based
                     authentication for IPsec VPN, TLS, and other
                     subsystems.";

        list ca {
            key "name";
            description "Trusted CA certificate. The certificate leaf
                         holds a base64-encoded DER X.509 certificate
                         (no PEM headers).";

            leaf name {
                type string;
                description "CA certificate name (referenced by consumers).";
            }

            leaf certificate {
                type string;
                mandatory true;
                description "Base64-encoded DER X.509 CA certificate.";
            }
        }

        list certificate {
            key "name";
            description "Device certificate with optional private key and
                         intermediate certificates.";

            leaf name {
                type string;
                description "Certificate name (referenced by consumers).";
            }

            leaf certificate {
                type string;
                mandatory true;
                description "Base64-encoded DER X.509 device certificate.";
            }

            leaf intermediate {
                type string;
                description "Base64-encoded DER intermediate CA certificate.
                             Stored alongside device cert for chain building.";
            }

            container private {
                description "Private key associated with this certificate.";

                leaf key {
                    type string;
                    ze:sensitive;
                    description "Private key in base64-encoded DER format.
                                 Stored as $9$ in config file, auto-decoded
                                 on load. Supports PKCS8, SEC1 (ECDSA),
                                 and PKCS1 (RSA) encodings.";
                }
            }
        }
    }
}
