module ze-ssh-conf {
    namespace "urn:ze:ssh:conf";
    prefix ssh;

    import ze-types { prefix zt; }
    import ze-extensions { prefix ze; }

    description "SSH server configuration for Ze";

    revision 2026-01-01 {
        description "Initial revision";
    }

    container system {
        description "System-level settings";

        container authentication {
            description "System authentication settings";

            list user {
                key "name";
                description "Authenticated user (local)";

                leaf name {
                    type string;
                    description "Username";
                }

                leaf password {
                    type string;
                    ze:bcrypt;
                    description "Bcrypt-hashed password (canonical form, e.g. $2a$10$...).
                                 Write plaintext via plaintext-password -- it is hashed
                                 into this leaf on commit and then discarded.";
                }

                leaf plaintext-password {
                    type string;
                    ze:ephemeral;
                    description "Write-only plaintext password. On commit, the config
                                 system bcrypt-hashes this value into the canonical
                                 password leaf and removes this one from the tree.
                                 Never persisted to the config file.";
                }

                leaf-list profile {
                    type string;
                    description "Authorization profile name(s) assigned to this user";
                }

                list public-keys {
                    key "name";
                    description "SSH public keys for key-based authentication.
                                 Each entry is a named key (e.g. user@host).";

                    leaf name {
                        type string;
                        description "Key identifier (e.g. jdoe@laptop)";
                    }

                    leaf type {
                        type enumeration {
                            enum ssh-rsa;
                            enum ssh-ed25519;
                            enum ecdsa-sha2-nistp256;
                            enum ecdsa-sha2-nistp384;
                            enum ecdsa-sha2-nistp521;
                        }
                        description "SSH public key algorithm";
                    }

                    leaf key {
                        type string;
                        description "Base64-encoded public key data (the middle field
                                     of an SSH public key line, without type prefix
                                     or comment suffix)";
                    }
                }
            }
        }
    }

    container environment {
        description "Environment settings for SSH server";

        container ssh {
            description "SSH server settings";

            leaf enabled {
                type boolean;
                default false;
                description "Enable SSH server";
            }

            list server {
                key "name";
                ze:listener;
                description "SSH server listen endpoints";

                leaf name {
                    type string;
                    description "Server instance name";
                }

                uses zt:listener {
                    refine ip {
                        default "0.0.0.0";
                    }
                    refine port {
                        default 2222;
                    }
                }
            }

            leaf host-key {
                type string;
                description "Path to SSH host key file (default: config dir + ssh_host_ed25519_key, auto-generated if missing)";
            }

            leaf host-certificate {
                type string;
                description "Path to SSH host certificate file (signed by a CA). Eliminates trust-on-first-use for clients that trust the CA.";
            }

            leaf idle-timeout {
                type uint32;
                description "Idle timeout in seconds (default 600)";
            }

            leaf max-sessions {
                type uint16;
                description "Maximum concurrent SSH sessions";
            }
        }
    }
}
