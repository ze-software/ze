module ze-update-show-cmd {
    namespace "urn:ze:update:show:cmd";
    prefix updateshowcmd;
    import ze-extensions { prefix ze; }
    description "show system update command tree. Owned by the update component because these handlers read the firmware update backend status. See ai/rules/plugin-self-containment.md.";
    revision 2026-06-06 { description "Relocated show system update out of the central show schema (plugin self-containment)."; }

    container show {
        config false;
        description "Read-only commands to inspect system, protocol, and network state";

        container system {
            config false;
            description "Daemon process and runtime diagnostics";

            container update {
                config false;
                ze:command "ze-show:system-update";
                description "Check if a firmware update is available.
Shows the running version, latest available version, and when the
last check ran. Use 'update system firmware check' to trigger an
immediate re-check.";

                container history {
                    config false;
                    ze:command "ze-show:system-update-history";
                    description "Show recent firmware update activity.
Lists the last 20 update events: checks, downloads, installs,
and rollbacks with timestamps and outcomes.";
                }
            }
        }
    }
}
