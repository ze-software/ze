module ze-web-conf {
    namespace "urn:ze:web:conf";
    prefix web;

    import ze-types { prefix zt; }
    import ze-extensions { prefix ze; }

    description "Web interface configuration for Ze";

    revision 2026-01-01 {
        description "Initial revision";
    }

    container environment {
        description "The web container under it carries every web interface setting: the
                     enable switch, the listen endpoints, the certificate and the UI
                     mode.";
        ze:help "Environment settings for the web interface.";

        container web {
            description "The container holds the enable switch, the listen endpoints, the
                         insecure switch, the certificate name and the UI mode.";
            ze:help "Web interface settings.";

            leaf enabled {
                type boolean;
                default false;
                description "The web interface does not start while this leaf is false,
                             and false is the default.";
                ze:help "Enable the web interface.";
            }

            list server {
                key "name";
                ze:listener;
                description "Each entry names one listen endpoint. The default endpoint
                             is 0.0.0.0 on port 3443.";
                ze:help "Web server listen endpoints.";

                leaf name {
                    type string;
                    description "The name is the list key, so each server entry carries a
                                 different one.";
                    ze:help "Server instance name.";
                }

                uses zt:listener {
                    refine ip {
                        default "0.0.0.0";
                    }
                    refine port {
                        default 3443;
                    }
                }
            }

            leaf insecure {
                type boolean;
                default false;
                description "With true, the web interface asks for no credentials. Ze
                             then binds it to 127.0.0.1, so only a user on the host
                             reaches it.";
                ze:help "Disable authentication, which forces the host to 127.0.0.1.";
            }

            leaf certificate {
                ze:reference "pki-certificate";
                type string {
                    length "1..255";
                    pattern '[A-Za-z0-9._-]+';
                }
                description
                    "The listener sends the leaf certificate and every
                     intermediate certificate the store entry holds, so a client
                     can build the full chain.
                     When this leaf is not set, ze generates a self-signed
                     certificate and serves that.
                     If the store holds no entry with that name, or the entry
                     holds no private key, ze exits with an error and rejects a
                     reload. ze never falls back to a self-signed certificate
                     for a configured name.
                     Environment variable: ze.web.certificate.";
                ze:help
                    "Name of the PKI store certificate served on the HTTPS listener (ze.web.certificate).";
            }

            leaf ui-mode {
                type enumeration {
                    enum finder { ze:help "Default file-browser style UI."; }
                    enum workbench { ze:help "Experimental workbench UI."; }
                }
                default "finder";
                description "finder is the default file-browser UI. workbench is the
                             experimental one.";
                ze:help "Web UI mode.";

            }
        }
    }
}
