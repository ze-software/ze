module ze-web-conf {
    namespace "urn:ze:web:conf";
    prefix web;

    import ze-types { prefix zt; }

    description "Web interface configuration for Ze";

    revision 2026-01-01 {
        description "Initial revision";
    }

    container environment {
        description "Environment settings for web interface";

        container web {
            description "Web interface settings";

            leaf host {
                type zt:ip-address;
                default "0.0.0.0";
                description "Listen host address";
            }

            leaf port {
                type uint16;
                default 3443;
                description "Listen port";
            }

            leaf insecure {
                type boolean;
                default false;
                description "Disable authentication (forces host to 127.0.0.1)";
            }
        }
    }
}
