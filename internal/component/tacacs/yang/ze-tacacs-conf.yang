module ze-tacacs-conf {
    namespace "urn:ze:tacacs:conf";
    prefix tacacs;

    import ze-types { prefix zt; }
    import ze-extensions { prefix ze; }
    import ze-authz-conf { prefix authz; }

    description "TACACS+ AAA configuration for Ze (RFC 8907)";

    revision 2026-04-15 {
        description "Initial revision";
    }

    container system {
        description "The container holds the system-wide settings. This module attaches
                     the TACACS+ server block and the tacacs-profile mapping under
                     authentication.";
        // Several modules declare this container and the config tree merges
        // them, so this text states what THIS module attaches under it.
        ze:help
            "System-level settings";

        container authentication {
            description "System authentication settings. This module attaches two nodes
                         under it. The tacacs block authenticates an operator login
                         against a TACACS+ server. The tacacs-profile list turns the
                         privilege level of that login into ze authorization profiles,
                         and a login whose level it does not map is denied. The TACACS+
                         backend joins the AAA chain at priority 100, behind RADIUS at
                         50 and in front of the local accounts at 200.";
            ze:help
                "System authentication settings";

            container tacacs {
                description "The TACACS+ backend joins the AAA chain at priority 100, in
                             front of the local backend at priority 200. Ze builds the
                             backend only where the server list holds one entry or more.
                             Authorization or accounting selected without a server is
                             a configuration error. Authentication runs as soon as one server exists.
                             Authorization and accounting are selected independently.
                             RFC 8907 Section 10.5 requires a network providing privacy,
                             integrity and separation from other traffic. TACACS+
                             obfuscation and source-address selection do not provide
                             those protections.";
                ze:help
                    "TACACS+ server configuration (RFC 8907)";

                list server {
                    key "address";
                    ordered-by user;
                    description "Ze tries the servers in the order you write them and
                                 moves to the next one when a connection or an exchange
                                 fails. The order is the config order, because the list
                                 is ordered-by user. Where every server fails, the AAA
                                 chain moves on to the local backend, so the local
                                 accounts still answer.";
                    ze:help
                        "TACACS+ servers, tried in configured order";

                    leaf address {
                        type zt:ip-address;
                        description "The type takes an IPv4 address or an IPv6 address,
                                     and it takes no hostname. The address is the list
                                     key, so one address holds one entry. Ze joins the
                                     address and the port with net.JoinHostPort, which
                                     puts an IPv6 address in brackets.";
                        ze:help
                            "Server IP address";
                    }

                    leaf port {
                        type uint16;
                        default 49;
                        description "Port 49 is the port IANA assigns to TACACS+, and
                                     RFC 8907 Section 3.4 names it. Ze opens one TCP
                                     connection to this port and reuses it where the
                                     server agrees to the single-connect flag. The type
                                     sets no lower bound, so a commit takes 0 and every
                                     connection to that server then fails.";
                        ze:help
                            "TCP port (default 49)";
                    }

                    leaf key {
                        type string {
                            length "1..max";
                        }
                        mandatory true;
                        ze:sensitive;
                        description "The key is the shared secret RFC 8907 Section 4.5
                                     builds the MD5 pseudo-pad from, and both ends must
                                     hold the same value. A client with no secret has no
                                     conformant packet to send. Section 10.5.2 requires
                                     a shared secret and forbids a client to set
                                     TAC_PLUS_UNENCRYPTED_FLAG. Omitting the key refuses
                                     the config: a commit, a load and a boot all stop
                                     on the missing mandatory field. The leaf is
                                     sensitive, so display paths mask it. Keys of 32
                                     characters or longer are supported. Use at least
                                     16 characters; doctor warns about shorter keys.
                                     A $9$-encoded value is decoded on read; this is
                                     reversible obfuscation, not encryption. Protect
                                     configuration files, exports and backups as secrets.";
                        ze:help
                            "Shared secret this server obfuscates its packets with";
                    }
                }

                leaf timeout {
                    type uint16 {
                        range "1..300";
                    }
                    default 5;
                    description "The value independently bounds a TCP connect and one
                                 request/reply exchange for each server. Servers are
                                 tried in order; a dead reused connection also permits
                                 one fresh connection attempt. Waiting for another
                                 exchange on a shared connection can add to this time.";
                    ze:help
                        "Per-server connection timeout in seconds";
                }

                leaf source-address {
                    type zt:ip-address;
                    description "Ze binds the local end of the outbound TCP connection to
                                 this address. Use it where the TACACS+ server accepts
                                 one address for this device, for example a loopback
                                 address. Where the leaf is absent, the kernel picks the
                                 address of the outgoing interface.";
                    ze:help
                        "Source IP for outbound TACACS+ connections";
                }

                leaf authorization {
                    type boolean;
                    default false;
                    description "The default false authorizes each command from the local
                                 profiles alone and sends the server nothing. Set it true
                                 and Ze sends an AUTHOR REQUEST for each command, with
                                 service=shell, cmd=<verb> and one cmd-arg for each
                                 argument (RFC 8907 Section 6). PASS_ADD and PASS_REPL
                                 permit execution only when the effective arguments
                                 describe the original command and every mandatory
                                 policy can be enforced. FAIL refuses the command.
                                 Ze sends privilege level 1 on these requests.";
                    ze:help
                        "Enable per-command TACACS+ authorization";
                }

                leaf strict-fallback {
                    type boolean;
                    default false;
                    description "The leaf decides one case: the server did not answer, or
                                 it answered ERROR or a status Ze does not know. The
                                 default false then authorizes the command from the local
                                 profiles, so a server outage does not lock the operator
                                 out. Set it true and Ze refuses the command instead.
                                 Neither value changes a FAIL from the server, which
                                 always refuses the command. The leaf reaches nothing
                                 while authorization is false.";
                    ze:help
                        "Deny authorization when TACACS+ is unavailable instead of falling back to local RBAC";
                }

                leaf accounting {
                    type boolean;
                    default false;
                    description "Set it true to account for every entered command,
                                 irrespective of its authorization method. A server is
                                 required. One worker sends START and STOP records from
                                 a bounded 64-record queue. A full queue delays command
                                 admission rather than losing a record; shutdown drains
                                 accepted records within the configured server timeout
                                 bounds. Transport failures are logged and do not deny
                                 command execution.";
                    ze:help
                        "Enable accounting for every entered command";
                }
            }

            list tacacs-profile {
                key "level";
                description "The list turns the privilege level Ze resolves for a
                             session into the ze authorization profiles of that session.
                             A level with no entry here denies the login, so this mapping
                             is what grants access, and not the PASS from the server. Ze
                             also removes a reserved profile name from the set, and a
                             level that then resolves to nothing denies the login too.";
                ze:help
                    "Maps TACACS+ privilege level to ze authorization profile";

                leaf level {
                    type uint8 {
                        range "0..15";
                    }
                    description "The level is the list key, so one level holds one entry.
                                 After PAP succeeds, Ze obtains priv-lvl from a shell
                                 session authorization (service=shell and an empty cmd).
                                 An absent priv-lvl uses level 1; authentication REPLY
                                 data never supplies privilege. RFC 8907 Section 9 states that 'Privilege
                                 levels are ordered values from 0 to 15 with each level
                                 being a superset of the next lower value'. Section 9
                                 also gives the common allocation: 0 for an
                                 unauthenticated session, 1 for a regular authenticated
                                 session, and 15 for the highest level. A level with no
                                 entry in this list denies the login, so every level the
                                 server can return needs an entry here.";
                    ze:help
                        "TACACS+ privilege level (0-15)";
                }

                leaf-list profile {
                    type leafref {
                        path "/authz:system/authz:authorization/authz:profile/authz:name";
                        require-instance true;
                    }
                    min-elements 1;
                    description "These local profiles govern the authenticated session. A commit rejects a
                                 name that no profile under system authorization defines, naming the
                                 profiles that exist. The path is absolute because the profile list lives
                                 in the ze-authz-conf module's system container, not this module's.
                                 A missing, empty or all-reserved profile mapping denies
                                 login. To deny a privilege level, omit its mapping.
                                 Local command authorization denies when none of the
                                 named profiles exists in the local policy store.";
                    ze:help "Ze authorization profiles for this privilege level. At least one is required.";
                }
            }
        }
    }
}
