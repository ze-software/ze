module ze-tacacs-cmd {
    namespace "urn:ze:tacacs:cmd";
    prefix tacacscmd;
    import ze-extensions { prefix ze; }
    description "show tacacs command tree. Owned by the tacacs component because the handler reads the TACACS+ server list a config file declares and dials each server. Container-merges onto the show verb root. See ai/rules/plugin-self-containment.md.";
    revision 2026-08-30 { description "Initial revision: declare show tacacs servers, so the reachability probe is a command the tree carries, completion offers and the pipe layer renders."; }

    container show {
        config false;
        description "Read-only commands to inspect system, protocol, and network state";

        container tacacs {
            config false;
            description "TACACS+ authentication server state";

            container servers {
                config false;
                ze:command "ze-show:tacacs-servers";
                description "Probe every TACACS+ server a config file names and report whether it answers.
Returns the address, port, reachability, round-trip time and dial error
for each server. Takes the path of the config file to read.";
                leaf config { type string { length "1..4096"; } mandatory true; description "Path of the config file whose TACACS+ servers are probed"; }
            }
        }
    }
}
