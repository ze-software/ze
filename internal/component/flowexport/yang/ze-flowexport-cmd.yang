module ze-flowexport-cmd {
    namespace "urn:ze:flowexport:cmd";
    prefix flowexportcmd;
    import ze-extensions { prefix ze; }
    description "show flow-export command tree. Owned by the flow-export component so that removing it removes the command node together with the handler. See ai/rules/plugin-self-containment.md.";
    revision 2026-06-03 { description "Relocated show flow-export out of the central show schema (plugin self-containment)."; }

    container show {
        config false;
        description "Read-only commands to inspect system, protocol, and network state";

        container flow-export {
            config false;
            ze:command "ze-show:flow-export";
            description "Show flow export (NetFlow/IPFIX) collector status.
Without arguments, lists all configured collectors. With 'name <name>',
shows details for that collector including protocol stats and errors.
Returns not-configured when no exporter is active.";
            leaf name {
                type string;
                description "Collector name (used with 'name <name>')";
            }
        }
    }
}
