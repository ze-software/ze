module ze-resolve-cmd {
    namespace "urn:ze:resolve:cmd";
    prefix resolvecmd;
    import ze-extensions { prefix ze; }
    description "Look up DNS, ASN, PeeringDB, and IRR data from the router";
    revision 2026-04-04 { description "Initial revision"; }

    container resolve {
        config false;
        description "DNS, ASN, PeeringDB, and IRR resolution tools";

        container dns {
            config false;
            description "DNS record lookups from the router";

            container a {
                config false;
                ze:command "ze-resolve:dns-a";
                description "Look up IPv4 addresses (A records) for a hostname.
Usage: resolve dns a <hostname>.";
            }
            container aaaa {
                config false;
                ze:command "ze-resolve:dns-aaaa";
                description "Look up IPv6 addresses (AAAA records) for a hostname.
Usage: resolve dns aaaa <hostname>.";
            }
            container txt {
                config false;
                ze:command "ze-resolve:dns-txt";
                description "Look up TXT records for a hostname.
Usage: resolve dns txt <hostname>. Returns all TXT strings.";
            }
            container ptr {
                config false;
                ze:command "ze-resolve:dns-ptr";
                description "Reverse-lookup an IP address to its hostname (PTR).
Usage: resolve dns ptr <ip-address>.";
            }
        }

        container cymru {
            config false;
            description "AS number lookups via Team Cymru";

            container asn-name {
                config false;
                ze:command "ze-resolve:cymru-asn-name";
                description "Find out who owns an AS number.
Queries Team Cymru DNS to return the organization name for the ASN.
Usage: resolve cymru asn-name <asn>.";
            }
        }

        container peeringdb {
            config false;
            description "PeeringDB lookups for peering information";

            container max-prefix {
                config false;
                ze:command "ze-resolve:peeringdb-max-prefix";
                description "Get max-prefix limits for an ASN from PeeringDB.
Returns IPv4 and IPv6 prefix limits. Use 'update bgp peer prefix'
to apply them automatically. Usage: resolve peeringdb max-prefix <asn>.";
            }
            container as-set {
                config false;
                ze:command "ze-resolve:peeringdb-as-set";
                description "Find the IRR AS-SET registered for an ASN in PeeringDB.
Usage: resolve peeringdb as-set <asn>. Feed the result into
'resolve irr expand' to get the full member list.";
            }
        }

        container ping {
            config false;
            ze:command "ze-resolve:ping";
            description "Ping from the router with optional source binding.
Usage: resolve ping <target> [source <ip>] [count <n>] [size <bytes>].";
        }

        container traceroute {
            config false;
            ze:command "ze-resolve:traceroute";
            description "Traceroute from the router with optional source binding.
Usage: resolve traceroute <target> [source <ip>].";
        }

        container irr {
            config false;
            description "Internet Routing Registry (WHOIS) queries";

            container expand {
                config false;
                ze:command "ze-resolve:irr-expand";
                description "Expand an AS-SET into its member AS numbers.
Recursively resolves nested AS-SET objects via WHOIS into a flat
list. Useful for building prefix filters from IRR data.";
            }
            container prefix {
                config false;
                ze:command "ze-resolve:irr-prefix";
                description "Get all prefixes announced by an AS-SET's members.
Expands the AS-SET, then returns every route/route6 object for
each member ASN. Use this to build or verify prefix filters.";
            }
        }
    }
}
