module ze-resolve-cmd {
    namespace "urn:ze:resolve:cmd";
    prefix resolvecmd;
    import ze-extensions { prefix ze; }
    description "Look up DNS, ASN, PeeringDB, and IRR data from the router, inspect the DNS cache, and clear the DNS resolver cache. Owned by the resolve component because every handler reads or resets the resolver (resolvers.DNS). Container-merges onto the resolve, show, and clear verb roots. See ai/rules/plugin-self-containment.md.";
    revision 2026-04-04 { description "Initial revision"; }
    revision 2026-06-03 { description "Relocated clear dns cache out of the central clear schema, and show dns lookup/cache out of the central show schema, into the resolve component (plugin self-containment)."; }

    container resolve {
        config false;
        description "DNS, ASN, PeeringDB, and IRR resolution tools";

        container dns {
            config false;
            description "DNS record lookups from the router";

            container a {
                config false;
                ze:command "ze-resolve:dns-a";
                description "Look up IPv4 addresses (A records) for a hostname.
Usage: resolve dns a <hostname>.";
            }
            container aaaa {
                config false;
                ze:command "ze-resolve:dns-aaaa";
                description "Look up IPv6 addresses (AAAA records) for a hostname.
Usage: resolve dns aaaa <hostname>.";
            }
            container txt {
                config false;
                ze:command "ze-resolve:dns-txt";
                description "Look up TXT records for a hostname.
Usage: resolve dns txt <hostname>. Returns all TXT strings.";
            }
            container ptr {
                config false;
                ze:command "ze-resolve:dns-ptr";
                description "Reverse-lookup an IP address to its hostname (PTR).
Usage: resolve dns ptr <ip-address>.";
            }
        }

        container cymru {
            config false;
            description "AS number lookups via Team Cymru";

            container asn-name {
                config false;
                ze:command "ze-resolve:cymru-asn-name";
                description "Find out who owns an AS number.
Queries Team Cymru DNS to return the organization name for the ASN.
Usage: resolve cymru asn-name <asn>.";
            }
        }

        container peeringdb {
            config false;
            description "PeeringDB lookups for peering information";

            container max-prefix {
                config false;
                ze:command "ze-resolve:peeringdb-max-prefix";
                description "Get max-prefix limits for an ASN from PeeringDB.
Returns IPv4 and IPv6 prefix limits. Use 'update bgp peer prefix'
to apply them automatically. Usage: resolve peeringdb max-prefix <asn>.";
            }
            container as-set {
                config false;
                ze:command "ze-resolve:peeringdb-as-set";
                description "Find the IRR AS-SET registered for an ASN in PeeringDB.
Usage: resolve peeringdb as-set <asn>. Feed the result into
'resolve irr expand' to get the full member list.";
            }
        }

        container irr {
            config false;
            description "Internet Routing Registry (WHOIS) queries";

            container expand {
                config false;
                ze:command "ze-resolve:irr-expand";
                description "Expand an AS-SET into its member AS numbers.
Recursively resolves nested AS-SET objects via WHOIS into a flat
list. Useful for building prefix filters from IRR data.";
            }
            container prefix {
                config false;
                ze:command "ze-resolve:irr-prefix";
                description "Get all prefixes announced by an AS-SET's members.
Expands the AS-SET, then returns every route/route6 object for
each member ASN. Use this to build or verify prefix filters.";
            }
        }
    }

    container show {
        config false;
        description "Read-only commands to inspect system, protocol, and network state";

        container dns {
            config false;
            description "DNS lookups and cache inspection";

            container lookup {
                config false;
                ze:command "ze-show:dns-lookup";
                description "Look up a DNS name from the router.
Resolves <hostname> using the daemon's DNS resolver (falls back to
the system resolver if no DNS component is configured). Default type
is A. Returns records, TTL, and query time. Supports A, AAAA, MX,
NS, TXT, CNAME, and PTR.";
                leaf hostname {
                    type string;
                    description "Hostname to resolve";
                }
                leaf type {
                    type enumeration {
                        enum A;
                        enum AAAA;
                        enum MX;
                        enum NS;
                        enum TXT;
                        enum CNAME;
                        enum PTR;
                    }
                    description "DNS record type";
                }
            }

            container cache {
                config false;
                ze:command "ze-show:dns-cache";
                description "Inspect the DNS cache.
'stats' shows hit/miss/eviction counters. 'list' shows all cached
entries. 'record <name>' shows one specific entry. Requires the DNS
component to be active.";
                leaf action {
                    type enumeration {
                        enum stats;
                        enum list;
                        enum record;
                    }
                    description "Cache operation";
                }
                leaf name {
                    type string;
                    description "Record name (for record action)";
                }
            }
        }
    }

    container clear {
        config false;
        description "Reset operational state without changing configuration";

        container dns {
            config false;
            description "DNS cache clearing operations";

            container cache {
                config false;
                ze:command "ze-clear:dns-cache";
                description "Clear the DNS cache.
With no argument, flushes everything. Use 'record <name>' to evict
one entry, or 'stats' to see hit/miss rates without flushing.";
            }
        }
    }
}
