module ze-telemetry-conf {
    namespace "urn:ze:telemetry:conf";
    prefix tel;

    import ze-types { prefix zt; }
    import ze-extensions { prefix ze; }

    description "Telemetry configuration for Ze";

    revision 2026-01-01 {
        description "Initial revision";
    }

    grouping netdata-collector-settings {
        description "Netdata-compatible OS collector settings";

        leaf prefix {
            type string;
            default "netdata";
            description "Ze puts the prefix in front of each Netdata-compatible OS
                         collector metric name. It does not change a Ze-native metric
                         name. The default is netdata.";
            ze:help "Metric name prefix for Netdata-compatible OS collector metrics only.";
        }

        leaf interval {
            type uint16 {
                range "1..60";
            }
            default 1;
            description "Each Netdata-compatible OS collector samples the operating
                         system once in this interval. The range is 1 to 60 seconds, and
                         the default is 1.";
            ze:help "Netdata-compatible OS collector sampling interval in seconds.";
        }

        list collector {
            key "name";
            description "Each entry names one collector, and it overrides the settings of
                         that collector alone.";
            ze:help "Per-Netdata-collector overrides of the enable state and the interval.";

            leaf name {
                type string;
                description "The collector names are cpu, memory, loadavg, netdev,
                             diskstats, stat, snmp, snmp6, conntrack, vmstat, sockstat,
                             sockstat6, softnet, softirqs, pressure, entropy, filenr,
                             uptime and diskspace.";
                ze:help "Collector name.";
            }

            leaf enabled {
                type boolean;
                default true;
                description "With false, Ze runs every other collector and stops this
                             one. The default is true.";
                ze:help "Enable or disable this Netdata-compatible OS collector.";
            }

            leaf interval {
                type uint16 {
                    range "1..60";
                }
                description "When this leaf is not set, the collector uses the global
                             Netdata interval.";
                ze:help "Override the sampling interval of this collector, in seconds.";
            }
        }
    }

    container telemetry {
        description "The container holds the Prometheus export settings and the Netdata-
                     compatible collector settings.";
        ze:help "Telemetry export configuration.";

        container prometheus {
            description "The container holds the enable switch, the listen endpoints, the
                         metrics path, the HTTP Basic Authentication settings and the
                         collector settings.";
            ze:help "Prometheus metrics HTTP export.";

            leaf enabled {
                type boolean;
                default false;
                description "Ze serves no metrics endpoint while this leaf is false, and
                             false is the default.";
                ze:help "Enable the Prometheus metrics endpoint.";
            }

            list server {
                key "name";
                ze:listener;
                description "Each entry names one listen endpoint. The default endpoint
                             is 127.0.0.1 on port 9273.";
                ze:help "Prometheus listen endpoints.";

                leaf name {
                    type string;
                    description "The name is the list key, so each server entry carries a
                                 different one.";
                    ze:help "Server instance name.";
                }

                uses zt:listener {
                    refine ip {
                        default "127.0.0.1";
                    }
                    refine port {
                        default 9273;
                    }
                }
            }

            leaf path {
                type string;
                default "/metrics";
                description "A scraper reads the metrics at this path on each listen
                             endpoint. The default path is /metrics.";
                ze:help "HTTP path of the metrics endpoint.";
            }

            container basic-auth {
                description "The container holds the enable switch, the realm, the
                             username and the two password leaves.";
                ze:help "HTTP Basic Authentication for the Prometheus service.";

                leaf enabled {
                    type boolean;
                    default false;
                    description "Ze asks for no credentials while this leaf is false, and
                                 false is the default.";
                    ze:help "Require HTTP Basic Authentication on the metrics and health endpoints.";
                }

                leaf realm {
                    type string;
                    default "ze prometheus";
                    description "A client shows the realm to the user when it asks for
                                 the credentials. The default is 'ze prometheus'.";
                    ze:help "HTTP Basic Authentication realm.";
                }

                leaf username {
                    type string;
                    description "The username pairs with the password leaf beside it.";
                    ze:help "HTTP Basic Authentication username.";
                }

                leaf password {
                    type string;
                    ze:bcrypt;
                    description "Ze compares the password of each request with this hash, and it
                                 compares the username in constant time. A value that is not a
                                 bcrypt hash stops the metrics server with an error, and the
                                 config check warns about it at commit. With basic-auth enabled,
                                 a username and this password are both required.";
                    ze:help "Bcrypt-hashed HTTP Basic Authentication password. Write plaintext via plaintext-password.";
                }

                leaf plaintext-password {
                    type string;
                    ze:ephemeral;
                    ze:sensitive;
                    description "On commit, the config system hashes this value into
                                 password and removes this leaf. The value is never
                                 written to the config file, and a display path renders
                                 the secret placeholder for it.";
                    ze:help "Write-only password.";
                }
            }

            container netdata {
                description "The default of enabled is true, so an absent container still runs
                             the collectors. The three settings under it replace the deprecated
                             prefix, interval and collector leaves beside this container. Ze
                             reads a deprecated leaf only when the matching leaf here is absent,
                             and it logs the path it read.";
                ze:help "Netdata-compatible OS collector metrics. These settings do not affect Ze-native metrics.";

                leaf enabled {
                    type boolean;
                    default true;
                    description "With false, Ze exports the Ze-native metrics alone. The
                                 default is true.";
                    ze:help "Enable the Netdata-compatible OS collectors.";
                }

                uses netdata-collector-settings;
            }

            leaf prefix {
                type string;
                default "netdata";
                status deprecated;
                description "The leaf sets the metric name prefix for Netdata-compatible
                             OS collector metrics only.";
                ze:help "Deprecated: use netdata/prefix.";
            }

            leaf interval {
                type uint16 {
                    range "1..60";
                }
                default 1;
                status deprecated;
                description "Write netdata/interval instead. Ze reads this leaf only when the
                             netdata container carries no interval leaf, and it then logs the
                             deprecated path it read. The range is 1 to 60 seconds and the
                             default is 1.";
                ze:help "Deprecated: use netdata/interval. Netdata-compatible OS collector sampling interval in seconds.";
            }

            list collector {
                key "name";
                status deprecated;
                description "Write netdata/collector instead. Ze reads this list only when the
                             netdata container carries no collector list, and it then logs the
                             deprecated path it read. A netdata collector list replaces this one
                             whole, and the two are never merged.";
                ze:help "Deprecated: use netdata/collector. Per-Netdata-collector overrides (enable/disable, interval).";

                leaf name {
                    type string;
                    description "The collector names are cpu, memory, loadavg, netdev,
                                 diskstats, stat, snmp, snmp6, conntrack, vmstat,
                                 sockstat, sockstat6, softnet, softirqs, pressure,
                                 entropy, filenr, uptime and diskspace.";
                    ze:help "Collector name.";
                }

                leaf enabled {
                    type boolean;
                    default true;
                    description "With false, Ze runs every other collector and stops this
                                 one. The default is true.";
                    ze:help "Enable or disable this collector.";
                }

                leaf interval {
                    type uint16 {
                        range "1..60";
                    }
                    description "The range is 1 to 60 seconds. An absent leaf gives the
                                 collector the interval of the netdata container. The leaf lives
                                 under a deprecated list, so write netdata/collector/interval
                                 instead.";
                    ze:help "Override sampling interval for this collector (seconds). Inherits global interval if not set.";
                }
            }
        }
    }
}
