module ze-telemetry-conf {
    namespace "urn:ze:telemetry:conf";
    prefix tel;

    import ze-types { prefix zt; }
    import ze-extensions { prefix ze; }

    description "Telemetry configuration for Ze";

    revision 2026-01-01 {
        description "Initial revision";
    }

    grouping netdata-collector-settings {
        description "Netdata-compatible OS collector settings";

        leaf prefix {
            type string;
            default "netdata";
            description "Metric name prefix for Netdata-compatible OS collector metrics only";
        }

        leaf interval {
            type uint16 {
                range "1..60";
            }
            default 1;
            description "Netdata-compatible OS collector sampling interval in seconds";
        }

        list collector {
            key "name";
            description "Per-Netdata-collector overrides (enable/disable, interval)";

            leaf name {
                type string;
                description "Collector name (cpu, memory, loadavg, netdev, diskstats, stat, snmp, snmp6, conntrack, vmstat, sockstat, sockstat6, softnet, softirqs, pressure, entropy, filenr, uptime, diskspace)";
            }

            leaf enabled {
                type boolean;
                default true;
                description "Enable or disable this Netdata-compatible OS collector";
            }

            leaf interval {
                type uint16 {
                    range "1..60";
                }
                description "Override sampling interval for this collector (seconds). Inherits global Netdata interval if not set.";
            }
        }
    }

    container telemetry {
        description "Telemetry export configuration";

        container prometheus {
            description "Prometheus metrics HTTP export";

            leaf enabled {
                type boolean;
                default false;
                description "Enable Prometheus metrics endpoint";
            }

            list server {
                key "name";
                ze:listener;
                description "Prometheus listen endpoints";

                leaf name {
                    type string;
                    description "Server instance name";
                }

                uses zt:listener {
                    refine ip {
                        default "127.0.0.1";
                    }
                    refine port {
                        default 9273;
                    }
                }
            }

            leaf path {
                type string;
                default "/metrics";
                description "HTTP path for metrics endpoint";
            }

            container basic-auth {
                description "HTTP Basic Authentication for the Prometheus service";

                leaf enabled {
                    type boolean;
                    default false;
                    description "Require HTTP Basic Authentication for Prometheus metrics and health endpoints";
                }

                leaf realm {
                    type string;
                    default "ze prometheus";
                    description "HTTP Basic Authentication realm";
                }

                leaf username {
                    type string;
                    description "HTTP Basic Authentication username";
                }

                leaf password {
                    type string;
                    ze:bcrypt;
                    description "Bcrypt-hashed HTTP Basic Authentication password. Write plaintext via plaintext-password.";
                }

                leaf plaintext-password {
                    type string;
                    ze:ephemeral;
                    description "Write-only password. On commit, the config system hashes this value into password and removes this leaf.";
                }
            }

            container netdata {
                description "Netdata-compatible OS collector metrics. These settings do not affect Ze-native metrics.";

                leaf enabled {
                    type boolean;
                    default true;
                    description "Enable Netdata-compatible OS collectors";
                }

                uses netdata-collector-settings;
            }

            leaf prefix {
                type string;
                default "netdata";
                status deprecated;
                description "Deprecated: use netdata/prefix. Metric name prefix for Netdata-compatible OS collector metrics only.";
            }

            leaf interval {
                type uint16 {
                    range "1..60";
                }
                default 1;
                status deprecated;
                description "Deprecated: use netdata/interval. Netdata-compatible OS collector sampling interval in seconds.";
            }

            list collector {
                key "name";
                status deprecated;
                description "Deprecated: use netdata/collector. Per-Netdata-collector overrides (enable/disable, interval).";

                leaf name {
                    type string;
                    description "Collector name (cpu, memory, loadavg, netdev, diskstats, stat, snmp, snmp6, conntrack, vmstat, sockstat, sockstat6, softnet, softirqs, pressure, entropy, filenr, uptime, diskspace)";
                }

                leaf enabled {
                    type boolean;
                    default true;
                    description "Enable or disable this collector";
                }

                leaf interval {
                    type uint16 {
                        range "1..60";
                    }
                    description "Override sampling interval for this collector (seconds). Inherits global interval if not set.";
                }
            }
        }
    }
}
