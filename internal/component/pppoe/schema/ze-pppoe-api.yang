module ze-pppoe-api {
    namespace "urn:ze:pppoe:api";
    prefix pppoeapi;

    description
        "PPPoE API operations for Ze. RPCs for observing session
         state and protocol counters. RFC 2516 supplies the field
         semantics (session ID, discovery tags).";

    revision 2026-05-08 {
        description "Initial PPPoE observability API (spec-bng-5-pppoe).";
    }

    rpc summary {
        description
            "Return subsystem summary: session count, interface count,
             aggregate state.";
        output {
            leaf summary {
                type string;
                description "JSON object with aggregate counters.";
            }
        }
    }

    rpc sessions {
        description "List every live PPPoE session across all interfaces.";
        output {
            leaf sessions {
                type string;
                description "JSON array of session objects.";
            }
        }
    }

    rpc session {
        description "Return one session by session ID.";
        input {
            leaf session-id {
                type uint16;
                mandatory true;
                description "PPPoE session ID (1..65535).";
            }
        }
        output {
            leaf session {
                type string;
                description "JSON object with session detail.";
            }
        }
    }

    rpc statistics {
        description
            "Return protocol counters: active sessions per interface,
             discovery packet counts.";
        output {
            leaf statistics {
                type string;
                description "JSON object with counter values.";
            }
        }
    }

    rpc interfaces {
        description "List configured PPPoE access interfaces.";
        output {
            leaf interfaces {
                type string;
                description "JSON array of interface objects.";
            }
        }
    }
}
