module ze-pppoe-conf {
    namespace "urn:ze:pppoe:conf";
    prefix pppoe;

    import ze-extensions { prefix ze; }

    description "PPPoE access concentrator configuration for Ze (RFC 2516).";

    revision 2026-05-08 {
        description "Initial revision (spec-bng-5-pppoe).";
    }

    container pppoe {
        description "PPPoE access concentrator settings (RFC 2516).
                     Presence of this block with any content implies the
                     subsystem is enabled. Use 'enabled false' to disable
                     explicitly, or 'enabled true' as a filler when no
                     other settings are needed.";

        leaf enabled {
            type boolean;
            default true;
            description "Enable PPPoE subsystem. Defaults to true when the
                         pppoe block is present; set to false to disable.";
        }

        leaf ac-name {
            type string;
            default "ze";
            description "Access Concentrator Name advertised in PADO (RFC 2516 Section 5.2).";
        }

        leaf-list service-name {
            type string;
            description "Accepted Service-Name values. Empty list means accept any
                         Service-Name (RFC 2516 Section 5.1). Per-interface
                         service-name overrides this global list.";
        }

        leaf cookie-timeout {
            type uint16 {
                range "1..300";
            }
            default 5;
            description "AC-Cookie validity duration in seconds. Cookies older
                         than this are rejected in PADR validation.";
        }

        leaf max-sessions {
            type uint16;
            default 65535;
            description "Maximum concurrent PPPoE sessions per interface.
                         Limited by the 16-bit session ID range (1-65535).";
        }

        leaf padi-rate-limit {
            type uint16 {
                range "1..10000";
            }
            default 100;
            description "Maximum PADI packets accepted per second per source MAC.
                         Excess PADIs are silently discarded.";
        }

        list interface {
            key "name";
            description "Access interfaces on which PPPoE discovery listens.
                         Each interface gets an independent session ID space.";

            leaf name {
                type string;
                description "Network interface name (e.g. eth0, eth0.100).";
            }

            leaf-list service-name {
                type string;
                description "Per-interface Service-Name filter. Overrides the
                             global service-name list when set.";
            }

            leaf max-sessions {
                type uint16;
                description "Per-interface session limit. Defaults to the global
                             max-sessions when unset.";
            }
        }
    }
}
