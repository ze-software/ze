module ze-bgp-conf {
    namespace "urn:ze:bgp:conf";
    prefix bgp;

    import ze-types { prefix zt; }
    import ze-extensions { prefix ze; }

    description "BGP configuration for ZeBGP";

    revision 2026-01-01 {
        description "Initial revision";
    }

    // Template block - peer templates
    container template {
        description "Peer templates";

        container bgp {
            description "BGP templates";
            list peer {
                key "pattern";
                description "Peer pattern template";

                leaf pattern {
                    type string;
                    description "Pattern to match peer addresses";
                }

                leaf inherit-name {
                    type string;
                    description "Named template identifier";
                }

                uses peer-fields;
            }
        }

        // Legacy syntax support
        list group {
            key "name";
            description "Legacy group template";
            leaf name { type string; }
            uses peer-fields;
        }

        list match {
            key "pattern";
            description "Legacy match template";
            leaf pattern { type string; }
            uses peer-fields;
        }
    }

    // BGP block - main BGP configuration
    container bgp {
        description "BGP configuration";

        leaf router-id {
            type zt:ipv4-address;
            mandatory true;
            description "BGP Router ID (required)";
        }

        leaf local-as {
            type zt:asn;
            mandatory true;
            description "Local Autonomous System Number (required)";
        }

        leaf listen {
            ze:syntax "multi-leaf";
            type string;
            description "Listen address and port";
        }

        list peer {
            key "address";
            description "BGP peer configuration";

            leaf address {
                type zt:ip-address;
                description "Peer IP address";
            }

            uses peer-fields;
        }
    }

    // Grouping for peer configuration fields
    grouping peer-fields {
        description "Common peer configuration fields";

        // Template inheritance
        leaf inherit {
            type string;
            description "Inherit from template";
        }

        // Basic peer identification
        leaf description {
            type string;
            description "Peer description";
        }

        leaf router-id {
            type zt:ipv4-address;
            description "Override router ID for this peer";
        }

        leaf local-address {
            type string;
            mandatory true;
            description "Local address for connection (use IP address or 'auto')";
        }

        leaf link-local {
            type string;
            description "IPv6 link-local address for next-hop (RFC 2545 Section 3)";
        }

        leaf local-as {
            type zt:asn;
            description "Local AS for this peer";
        }

        leaf peer-as {
            type zt:asn;
            mandatory true;
            description "Peer Autonomous System Number (required)";
        }

        leaf hold-time {
            type uint16 {
                range "0 | 3..65535";
            }
            default 90;
            description "Hold time in seconds (RFC 4271: 0 or >= 3)";
        }

        leaf passive {
            type boolean;
            default false;
            description "Wait for peer to connect";
        }

        leaf group-updates {
            type boolean;
            default true;
            description "Group UPDATE messages";
        }

        // Address families - special FamilyBlock syntax
        container family {
            ze:syntax "family-block";
            description "Address families to negotiate";
        }

        // Capabilities
        container capability {
            description "BGP capability negotiation";

            leaf asn4 {
                type boolean;
                default true;
                description "4-byte ASN support";
            }

            container route-refresh {
                ze:syntax "flex";
                description "Route Refresh capability";
            }

            // NOTE: graceful-restart moved to GR plugin (ze-graceful-restart.yang)

            container add-path {
                ze:syntax "flex";
                description "ADD-PATH capability";
                leaf send {
                    type boolean;
                    default false;
                    description "Send ADD-PATH";
                }
                leaf receive {
                    type boolean;
                    default false;
                    description "Receive ADD-PATH";
                }
            }

            container extended-message {
                ze:syntax "flex";
                description "Extended Message capability";
            }

            container nexthop {
                ze:syntax "freeform";
                description "Extended Next Hop capability";
            }

            container multi-session {
                ze:syntax "flex";
                description "Multi-session capability";
            }

            container operational {
                ze:syntax "flex";
                description "Operational capability";
            }

            container aigp {
                ze:syntax "flex";
                description "AIGP capability";
            }

            container software-version {
                ze:syntax "flex";
                description "Software Version capability";
            }
        }

        // Additional peer settings
        // NOTE: host-name/domain-name moved to hostname plugin (ze-hostname.yang)

        leaf md5-password {
            type string;
            description "MD5 authentication password";
        }

        leaf md5-ip {
            type zt:ip-address;
            description "MD5 authentication IP";
        }

        leaf ttl-security {
            type uint16;
            description "TTL security (GTSM)";
        }

        leaf outgoing-ttl {
            type uint16;
            description "Outgoing TTL";
        }

        leaf incoming-ttl {
            type uint16;
            description "Incoming TTL";
        }

        leaf multi-session {
            type boolean;
            default false;
            description "Multi-session mode";
        }

        leaf manual-eor {
            type boolean;
            description "Manual End-of-RIB";
        }

        leaf auto-flush {
            type boolean;
            description "Auto-flush routes";
        }

        leaf adj-rib-out {
            type boolean;
            description "Maintain Adj-RIB-Out";
        }

        leaf adj-rib-in {
            type boolean;
            description "Maintain Adj-RIB-In";
        }

        // Native update syntax - Ze-native route announcements
        // update { attribute { origin igp; next-hop 10.0.0.1; } nlri { ipv4/unicast 1.0.0.0/24; } }
        list update {
            description "Native Ze route announcements";

            container attribute {
                description "Path attributes for routes in this block";
                leaf origin {
                    type enumeration {
                        enum igp { description "Interior Gateway Protocol"; }
                        enum egp { description "Exterior Gateway Protocol"; }
                        enum incomplete { description "Incomplete origin"; }
                    }
                    description "ORIGIN attribute (RFC 4271 Section 4.3)";
                }
                leaf next-hop { type string; description "Next hop address or 'self'"; }
                leaf med { type uint32; description "Multi-Exit Discriminator"; }
                leaf local-preference { type uint32; description "Local preference"; }
                leaf as-path { ze:syntax "value-or-array"; type string; description "AS path"; }
                leaf community { ze:syntax "value-or-array"; type string; description "Communities"; }
                leaf large-community { ze:syntax "value-or-array"; type string; description "Large communities"; }
                leaf extended-community { ze:syntax "value-or-array"; type string; description "Extended communities"; }
                leaf label { type string; description "MPLS label"; }
                leaf labels { ze:syntax "value-or-array"; type string; description "Multi-label stack (RFC 8277)"; }
                leaf path-information { type string; description "ADD-PATH path-id"; }
                leaf rd { type string; description "Route Distinguisher (RFC 4364)"; }
                leaf aggregator { type string; description "Aggregator AS:IP"; }
                leaf atomic-aggregate { type boolean; description "Atomic aggregate flag"; }
                leaf originator-id { type zt:ipv4-address; description "Originator ID"; }
                leaf cluster-list { ze:syntax "value-or-array"; type string; description "Cluster list"; }
                leaf attribute { ze:syntax "value-or-array"; type string; description "Generic hex attributes"; }
                leaf bgp-prefix-sid { ze:syntax "flex"; type string; description "Prefix-SID (label index)"; }
                leaf bgp-prefix-sid-srv6 { ze:syntax "flex"; type string; description "SRv6 Prefix-SID"; }
                leaf split { type string; description "Prefix splitting"; }
            }

            container nlri {
                ze:syntax "freeform";
                description "NLRI by family: ipv4/unicast, ipv6/unicast, etc.";
            }

            container watchdog {
                description "Watchdog-controlled route - held until 'bgp watchdog announce <name>'";
                leaf name { type string; description "Watchdog group name"; }
                leaf withdraw { type boolean; description "Start in withdrawn state (default true)"; }
            }
        }

        // Add-path configuration
        container add-path {
            ze:syntax "freeform";
            description "Per-family ADD-PATH configuration";
        }

        // Process bindings
        list process {
            key "name";
            description "Process binding";

            leaf name {
                type string;
                description "Process name";
            }

            leaf run {
                type string;
                description "Command to execute";
            }

            // Old syntax fields
            leaf-list processes {
                ze:syntax "bracket";
                type string;
                description "Process list";
            }

            leaf-list processes-match {
                ze:syntax "bracket";
                type string;
                description "Process match patterns";
            }

            container neighbor-changes {
                ze:syntax "flex";
                description "Neighbor change notifications";
            }

            // New syntax fields
            container content {
                description "Content configuration";
                leaf encoding { type string; }
                leaf format { type string; }
                leaf attribute { type string; }
                container nlri {
                    ze:syntax "flex";
                    description "NLRI families";
                }
            }

            container receive {
                ze:syntax "freeform";
                description "Receive configuration";
            }

            container send {
                ze:syntax "freeform";
                description "Send configuration";
            }
        }

        // FlowSpec routes (RFC 8955)
        container flow {
            description "FlowSpec route definitions";
            list route {
                key "name";
                leaf name { type string; description "Route name"; }
                leaf rd { type string; description "Route Distinguisher"; }
                leaf next-hop { type string; description "Next hop address"; }
                container match { ze:syntax "freeform"; description "Match criteria"; }
                container then { ze:syntax "freeform"; description "Actions"; }
            }
        }

        // RIB configuration
        container rib {
            description "RIB configuration";
            container out {
                description "Outbound RIB settings";
                leaf group-updates {
                    type boolean;
                    default true;
                    description "Group updates";
                }
                leaf auto-commit-delay {
                    type string;
                    default "0";
                    description "Auto-commit delay";
                }
                leaf max-batch-size {
                    type int32;
                    default 0;
                    description "Max batch size";
                }
            }
        }

    }
}
