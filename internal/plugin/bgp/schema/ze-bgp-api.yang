module ze-bgp-api {
    namespace "urn:ze:bgp:api";
    prefix bgpapi;

    import ze-types { prefix zt; }

    description
        "BGP API operations for Ze.
         RPCs for peer management, route operations, cache control,
         and event subscriptions. Notifications for BGP events.";

    revision 2026-02-01 {
        description "Initial revision";
    }

    // Introspection

    rpc help {
        description "List BGP subcommands";
        output {
            leaf-list subcommands { type string; description "Available subcommands"; }
        }
    }

    rpc command-list {
        description "List BGP commands";
        output {
            list command {
                uses zt:command-info;
            }
        }
    }

    rpc command-help {
        description "Show BGP command details";
        input {
            leaf name { type string; mandatory true; description "Command name"; }
        }
        output {
            leaf help { type string; description "Detailed help text"; }
        }
    }

    rpc command-complete {
        description "Complete BGP command/args";
        input {
            leaf partial { type string; mandatory true; description "Partial command string"; }
        }
        output {
            leaf-list completions { type string; description "Completion candidates"; }
        }
    }

    // Plugin configuration

    rpc plugin-encoding {
        description "Set event encoding (json|text)";
        input {
            leaf encoding { type zt:encoding-mode; mandatory true; description "Encoding format"; }
        }
    }

    rpc plugin-format {
        description "Set wire format (hex|base64|parsed|full)";
        input {
            leaf format { type zt:wire-format; mandatory true; description "Wire format"; }
        }
    }

    rpc plugin-ack {
        description "Set ACK timing (sync|async)";
        input {
            leaf mode { type zt:ack-mode; mandatory true; description "ACK mode"; }
        }
    }

    // Peer operations

    rpc peer-list {
        description "List configured peers";
        input {
            leaf selector { type zt:peer-selector; description "Peer filter"; }
        }
        output {
            list peer {
                uses zt:peer-info;
            }
        }
    }

    rpc peer-show {
        description "Show detailed peer information";
        input {
            leaf selector { type zt:peer-selector; description "Peer filter"; }
        }
        output {
            list peer {
                uses zt:peer-info;
            }
        }
    }

    rpc peer-add {
        description "Add a new peer";
        input {
            leaf address { type zt:ip-address; mandatory true; description "Peer address"; }
            leaf asn { type zt:asn; mandatory true; description "Peer ASN"; }
            leaf local-as { type zt:asn; description "Local ASN override"; }
            leaf local-address { type zt:ip-address; description "Local bind address"; }
            leaf router-id { type zt:ipv4-address; description "Router ID override"; }
            leaf hold-time { type uint16; description "Hold time"; }
            leaf passive { type boolean; description "Passive mode"; }
        }
    }

    rpc peer-remove {
        description "Remove a peer";
        input {
            leaf address { type zt:ip-address; mandatory true; description "Peer address"; }
        }
    }

    rpc peer-teardown {
        description "Teardown peer session with CEASE notification";
        input {
            leaf selector { type zt:peer-selector; mandatory true; description "Peer filter"; }
            leaf subcode { type uint8; description "CEASE subcode"; }
        }
    }

    // Route operations

    rpc peer-update {
        description "Batch UPDATE with text/hex/b64 encoding";
        input {
            leaf peer-selector { type zt:peer-selector; mandatory true; description "Target peers"; }
            leaf encoding { type zt:encoding-mode; mandatory true; description "Command encoding"; }
            leaf command { type string; mandatory true; description "Route DSL command"; }
        }
        output {
            leaf peers-affected { type uint32; description "Number of peers affected"; }
            leaf routes-sent { type uint32; description "Number of routes sent"; }
        }
    }

    rpc watchdog-announce {
        description "Announce watchdog group routes";
        input {
            leaf group { type string; mandatory true; description "Watchdog group name"; }
        }
    }

    rpc watchdog-withdraw {
        description "Withdraw watchdog group routes";
        input {
            leaf group { type string; mandatory true; description "Watchdog group name"; }
        }
    }

    // Route refresh (RFC 7313)

    rpc peer-borr {
        description "Send Beginning of Route Refresh";
        input {
            leaf peer-selector { type zt:peer-selector; mandatory true; description "Target peers"; }
            leaf family { type zt:address-family; mandatory true; description "Address family"; }
        }
    }

    rpc peer-eorr {
        description "Send End of Route Refresh";
        input {
            leaf peer-selector { type zt:peer-selector; mandatory true; description "Target peers"; }
            leaf family { type zt:address-family; mandatory true; description "Address family"; }
        }
    }

    // Raw message

    rpc peer-raw {
        description "Send raw bytes to peer (no validation)";
        input {
            leaf peer-selector { type zt:peer-selector; mandatory true; description "Target peers"; }
            leaf type { type string; description "Message type hint"; }
            leaf encoding { type zt:encoding-mode; mandatory true; description "Data encoding"; }
            leaf data { type string; mandatory true; description "Raw data"; }
        }
    }

    // Cache operations

    rpc cache {
        description "BGP message cache operations";
        input {
            leaf action { type string; mandatory true; description "Cache action (list|retain|release|expire|forward)"; }
            leaf message-id { type uint64; description "Cache message ID"; }
            leaf peer-selector { type zt:peer-selector; description "Target peers (for forward)"; }
        }
    }

    // Commit operations

    rpc commit {
        description "Named commit operations";
        input {
            leaf name { type string; description "Commit name"; }
        }
    }

    // Subscription

    rpc subscribe {
        description "Subscribe to BGP events (streaming)";
        input {
            leaf-list events { type string; description "Event types to subscribe to"; }
        }
    }

    rpc unsubscribe {
        description "Unsubscribe from BGP events";
    }

    rpc event-list {
        description "List available event types";
        output {
            list event {
                uses zt:event-type-info;
            }
        }
    }

    // Notifications

    notification peer-state-change {
        description "Peer FSM state changed";
        leaf address { type zt:ip-address; description "Peer address"; }
        leaf old-state { type string; description "Previous FSM state"; }
        leaf new-state { type string; description "New FSM state"; }
    }

    notification route-received {
        description "BGP UPDATE received from peer";
        leaf peer { type zt:ip-address; description "Source peer"; }
        leaf family { type zt:address-family; description "Address family"; }
        leaf count { type uint32; description "Number of NLRI in update"; }
    }

    notification route-update-sent {
        description "BGP UPDATE sent to peer";
        leaf peer { type zt:ip-address; description "Target peer"; }
        leaf family { type zt:address-family; description "Address family"; }
    }

    notification eor-received {
        description "End-of-RIB marker received";
        leaf peer { type zt:ip-address; description "Source peer"; }
        leaf family { type zt:address-family; description "Address family"; }
    }

    notification graceful-restart-state {
        description "Graceful restart state changed";
        leaf peer { type zt:ip-address; description "Peer address"; }
        leaf state { type string; description "GR state"; }
    }

    notification session-established {
        description "BGP session established";
        leaf peer { type zt:ip-address; description "Peer address"; }
        leaf asn { type zt:asn; description "Peer ASN"; }
    }

    notification session-closed {
        description "BGP session closed";
        leaf peer { type zt:ip-address; description "Peer address"; }
        leaf reason { type string; description "Close reason"; }
    }
}
