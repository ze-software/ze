module ze-rib-api {
    namespace "urn:ze:rib:api";
    prefix ribapi;

    import ze-types { prefix zt; }

    description
        "RIB API operations for Ze.
         RPCs for querying and clearing RIB state.
         Notifications for RIB changes.";

    revision 2026-02-01 {
        description "Initial revision";
    }

    // Introspection

    rpc help {
        description "Show RIB subcommands";
        output {
            leaf-list subcommands { type string; description "Available subcommands"; }
        }
    }

    rpc command-list {
        description "List RIB commands";
        output {
            list command {
                leaf name { type string; description "Command name"; }
                leaf description { type string; description "Command description"; }
            }
        }
    }

    rpc command-help {
        description "Show RIB command details";
        input {
            leaf name { type string; mandatory true; description "Command name"; }
        }
        output {
            leaf help { type string; description "Detailed help text"; }
        }
    }

    rpc command-complete {
        description "Complete RIB command/args";
        input {
            leaf partial { type string; mandatory true; description "Partial command string"; }
        }
        output {
            leaf-list completions { type string; description "Completion candidates"; }
        }
    }

    rpc event-list {
        description "List RIB event types";
        output {
            list event {
                leaf name { type string; description "Event type name"; }
                leaf description { type string; description "Event description"; }
            }
        }
    }

    // RIB operations

    rpc show-in {
        description "Show Adj-RIB-In entries";
        input {
            leaf peer { type zt:ip-address; description "Filter by peer"; }
            leaf family { type zt:address-family; description "Filter by address family"; }
        }
        output {
            leaf route-count { type uint32; description "Number of routes"; }
        }
    }

    rpc clear-in {
        description "Clear Adj-RIB-In entries";
        input {
            leaf peer { type zt:ip-address; description "Filter by peer"; }
            leaf family { type zt:address-family; description "Filter by address family"; }
        }
    }

    rpc show-out {
        description "Show Adj-RIB-Out entries";
        input {
            leaf peer { type zt:ip-address; description "Filter by peer"; }
            leaf family { type zt:address-family; description "Filter by address family"; }
        }
        output {
            leaf route-count { type uint32; description "Number of routes"; }
        }
    }

    rpc clear-out {
        description "Clear Adj-RIB-Out entries";
        input {
            leaf peer { type zt:ip-address; description "Filter by peer"; }
            leaf family { type zt:address-family; description "Filter by address family"; }
        }
    }

    // Notifications

    notification rib-change {
        description "RIB content changed";
        leaf peer { type zt:ip-address; description "Affected peer"; }
        leaf family { type zt:address-family; description "Address family"; }
        leaf added { type uint32; description "Routes added"; }
        leaf removed { type uint32; description "Routes removed"; }
    }
}
