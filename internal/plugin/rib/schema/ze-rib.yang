module ze-rib {
    namespace "urn:ze:rib";
    prefix rib;

    import ze-bgp-conf { prefix bgp; }

    description
        "RIB (Routing Information Base) plugin for Ze.
         Tracks Adj-RIB-In (routes from peers) and Adj-RIB-Out (routes to peers).
         Supports ADD-PATH (RFC 7911) with per-path-id storage.";

    revision 2025-01-31 {
        description "Initial revision.";
    }

    augment "/bgp:bgp" {
        container rib {
            description "RIB plugin state and operations.";
            config false;

            container adj-rib-in {
                description "Routes received from peers.";

                list peer {
                    key "address";
                    description "Per-peer Adj-RIB-In.";

                    leaf address {
                        type string;
                        description "Peer IP address.";
                    }

                    leaf route-count {
                        type uint32;
                        description "Number of routes from this peer.";
                    }
                }
            }

            container adj-rib-out {
                description "Routes sent to peers.";

                list peer {
                    key "address";
                    description "Per-peer Adj-RIB-Out.";

                    leaf address {
                        type string;
                        description "Peer IP address.";
                    }

                    leaf route-count {
                        type uint32;
                        description "Number of routes to this peer.";
                    }
                }
            }
        }
    }
}
