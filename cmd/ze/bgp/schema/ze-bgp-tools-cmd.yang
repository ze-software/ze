module ze-bgp-tools-cmd {
    namespace "urn:ze:bgp:tools:cmd";
    prefix bgptoolscmd;
    import ze-extensions { prefix ze; }
    description "Offline BGP protocol tools (decode/encode). Owned by cmd/ze/bgp so that removing the BGP command surface removes show bgp decode/encode. See ai/rules/plugin-self-containment.md.";
    revision 2026-06-02 { description "Relocated show bgp decode/encode out of the central show schema (plugin self-containment)."; }

    container show {
        config false;
        description "Read-only commands to inspect system, protocol, and network state";

        container bgp {
            config false;
            description "BGP peers, sessions, RIB, and protocol tools";

            container decode {
                config false;
                ze:command "ze-show:bgp-decode";
                description "Decode a hex-encoded BGP message into readable JSON.
Paste a hex BGP UPDATE and get back parsed attributes, NLRI, and
withdrawn prefixes. Handy for reading pcap captures or debugging
wire issues. Also available in the web UI under tools.";
            }

            container encode {
                config false;
                ze:command "ze-show:bgp-encode";
                description "Turn a route announcement into wire-format hex.
Takes a route in API syntax and returns the BGP UPDATE as a hex
string. Useful for building test payloads, feeding to ze-test, or
verifying that your announcement encodes correctly.";
            }
        }
    }
}
