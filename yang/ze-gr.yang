module ze-gr {
    namespace "urn:ze:gr";
    prefix gr;

    import ze-bgp { prefix bgp; }

    description "Graceful Restart plugin for ZeBGP";

    revision 2026-01-01 {
        description "Initial revision";
    }

    augment "/bgp:bgp/bgp:peer/bgp:capability" {
        description "GR configuration for peers";

        container graceful-restart {
            description "RFC 4724 Graceful Restart configuration";

            leaf enabled {
                type boolean;
                default false;
                description "Enable Graceful Restart capability";
            }

            leaf restart-time {
                type uint16 {
                    range "0..4095";
                }
                default 120;
                description "Restart time in seconds (0-4095 per RFC 4724)";
            }
        }
    }

    augment "/bgp:bgp/bgp:peer-group/bgp:capability" {
        description "GR configuration for peer-groups";

        container graceful-restart {
            description "RFC 4724 Graceful Restart configuration";

            leaf enabled {
                type boolean;
                default false;
                description "Enable Graceful Restart capability";
            }

            leaf restart-time {
                type uint16 {
                    range "0..4095";
                }
                default 120;
                description "Restart time in seconds (0-4095 per RFC 4724)";
            }
        }
    }
}
